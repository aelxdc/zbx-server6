--UPS3P-MIB { iso(1) org(3) dod(6) internet(1) private(4)
--      enterprises(1) rcmib(2350) }


UPS3P-MIB DEFINITIONS ::= BEGIN
-- Title: PPC TOP LEVEL MIB
-- Date: January 07, 1994    Version 1.00
--
-- Date: January 17, 1994    Version 1.01
--
-- Date: July 14, 1994    Version 1.02


IMPORTS
	MODULE-IDENTITY, OBJECT-TYPE, Integer32, NOTIFICATION-TYPE                       
        FROM SNMPv2-SMI
	enterprises, IpAddress
		FROM RFC1155-SMI
	DisplayString
		FROM RFC1213-MIB
	OBJECT-TYPE
		FROM RFC-1212
	TRAP-TYPE
		FROM RFC-1215;

rcmib                           OBJECT IDENTIFIER ::=  { enterprises 2350 }

products                        OBJECT IDENTIFIER ::=  { rcmib 1 }

upsI3p	                        OBJECT IDENTIFIER ::=  { products 1 }
upsII3p	                        OBJECT IDENTIFIER ::=  { products 2 }
upsIII3p	                        OBJECT IDENTIFIER ::=  { products 3 }
upsIV3p	                        OBJECT IDENTIFIER ::=  { products 4 }
ups3pTraps                      OBJECT IDENTIFIER ::=  { products 5 }

upsI3pAnalog                       OBJECT IDENTIFIER ::=  { upsI3p 1 }
upsI3pSwitch                       OBJECT IDENTIFIER ::=  { upsI3p 2 }
upsI3pControl                      OBJECT IDENTIFIER ::=  { upsI3p 3 }
upsI3pStrInfo                      OBJECT IDENTIFIER ::=  { upsI3p 4 }

-- the upsI3pAnalog group

upsI3pAutoRestartType OBJECT-TYPE
	SYNTAX INTEGER {
		automatic(0),
		manual(100)
	}
	ACCESS read-only
	STATUS mandatory
	DESCRIPTION
		"The current UPS automatic restart type"
	::= { upsI3pAnalog 21 }

upsI3pShutdownType OBJECT-TYPE
	SYNTAX INTEGER {
		shutdownOutputOnly(0),
		Entire(100)
	}
	ACCESS read-only
	STATUS mandatory
	DESCRIPTION
		"The current UPS shutdown type"
	::= { upsI3pAnalog 22 }

upsI3pBatCondition OBJECT-TYPE
	SYNTAX INTEGER {
		good(0),
		weak(100),
		replace(200)
	}
	ACCESS read-only
	STATUS mandatory
	DESCRIPTION
		"The current Battery Condition"
	::= { upsI3pAnalog 23 }

upsI3pBatStatus OBJECT-TYPE
	SYNTAX INTEGER {
		OK(0),
		Low(100),
		Depleted(200)
	}
	ACCESS read-only
	STATUS mandatory
	DESCRIPTION
		"The current Battery Status"
	::= { upsI3pAnalog 24 }

upsI3pBatChargeStatus OBJECT-TYPE
	SYNTAX INTEGER {
		floating(0),
		charging(100),
		resting(200),
		discharging(300)
	}
	ACCESS read-only
	STATUS mandatory
	DESCRIPTION
		"The current Battery Charge Status"
	::= { upsI3pAnalog 25 }

--upsI3pSecondOnBattery OBJECT-TYPE
--	SYNTAX INTEGER
--	ACCESS read-only
--	STATUS mandatory
--	DESCRIPTION
--		"The current UPS Senond On Battery in 1/100 Second"
--	::= { upsI3pAnalog 26 }

upsI3pEstimatedMinutesOnBat OBJECT-TYPE
	SYNTAX INTEGER
	ACCESS read-only
	STATUS mandatory
	DESCRIPTION
		"The current UPS estimated Minutes On Battery in 1/100 Minutes"
	::= { upsI3pAnalog 26 }

upsI3pEstimatedCharge OBJECT-TYPE
	SYNTAX INTEGER
	ACCESS read-only
	STATUS mandatory
	DESCRIPTION
		"The current UPS estimated Charge in 1/100 %"
	::= { upsI3pAnalog 28 }

upsI3pBatteryVol OBJECT-TYPE
	SYNTAX INTEGER
	ACCESS read-only
	STATUS mandatory
	DESCRIPTION
		"The current UPS Battery voltage in 1/100 V"
	::= { upsI3pAnalog 29 }

upsI3pBatteryCurrent OBJECT-TYPE
	SYNTAX INTEGER
	ACCESS read-only
	STATUS mandatory
	DESCRIPTION
		"The current UPS Battery Current in 1/100 A"
	::= { upsI3pAnalog 30 }

upsI3pBatteryTemperature OBJECT-TYPE
	SYNTAX INTEGER
	ACCESS read-only
	STATUS mandatory
	DESCRIPTION
		"The current UPS Battery Temperature in 1/100 C"
	::= { upsI3pAnalog 31 }

upsI3pInputLineBads OBJECT-TYPE
	SYNTAX INTEGER
	ACCESS read-only
	STATUS mandatory
	DESCRIPTION
		"The current UPS Input line bads in 1/100 line"
	::= { upsI3pAnalog 32 }

upsI3pInputLines OBJECT-TYPE
	SYNTAX INTEGER
	ACCESS read-only
	STATUS mandatory
	DESCRIPTION
		"The current UPS Input line in 1/100 line"
	::= { upsI3pAnalog 33 }

upsI3pInputLine1Fre OBJECT-TYPE
	SYNTAX INTEGER
	ACCESS read-only
	STATUS mandatory
	DESCRIPTION
		"The current UPS Input Line1 Fre in 1/100 Hz"
	::= { upsI3pAnalog 34 }

upsI3pInputLine1Vol OBJECT-TYPE
	SYNTAX INTEGER
	ACCESS read-only
	STATUS mandatory
	DESCRIPTION
		"The current UPS Input Line1 voltage in 1/100 V"
	::= { upsI3pAnalog 35 }

upsI3pInputLine1Cur OBJECT-TYPE
	SYNTAX INTEGER
	ACCESS read-only
	STATUS mandatory
	DESCRIPTION
		"The current UPS Input Line1 Current in 1/100 A"
	::= { upsI3pAnalog 36 }

upsI3pInputLine1Power OBJECT-TYPE
	SYNTAX INTEGER
	ACCESS read-only
	STATUS mandatory
	DESCRIPTION
		"The current UPS Input Line1 Power in 1/100 KW"
	::= { upsI3pAnalog 37 }

upsI3pInputLine2Fre OBJECT-TYPE
	SYNTAX INTEGER
	ACCESS read-only
	STATUS mandatory
	DESCRIPTION
		"The current UPS Input Line2 Fre in 1/100 Hz"
	::= { upsI3pAnalog 38 }

upsI3pInputLine2Vol OBJECT-TYPE
	SYNTAX INTEGER
	ACCESS read-only
	STATUS mandatory
	DESCRIPTION
		"The current UPS Input Line2 voltage in 1/100 V"
	::= { upsI3pAnalog 39 }

upsI3pInputLine2Cur OBJECT-TYPE
	SYNTAX INTEGER
	ACCESS read-only
	STATUS mandatory
	DESCRIPTION
		"The current UPS Input Line2 Current in 1/100 A"
	::= { upsI3pAnalog 40 }

upsI3pInputLine2Power OBJECT-TYPE
	SYNTAX INTEGER
	ACCESS read-only
	STATUS mandatory
	DESCRIPTION
		"The current UPS Input Line2 Power in 1/100 KW"
	::= { upsI3pAnalog 41 }

upsI3pInputLine3Fre OBJECT-TYPE
	SYNTAX INTEGER
	ACCESS read-only
	STATUS mandatory
	DESCRIPTION
		"The current UPS Input Line3 Fre in 1/100 Hz"
	::= { upsI3pAnalog 42 }

upsI3pInputLine3Vol OBJECT-TYPE
	SYNTAX INTEGER
	ACCESS read-only
	STATUS mandatory
	DESCRIPTION
		"The current UPS Input Line3 voltage in 1/100 V"
	::= { upsI3pAnalog 43 }

upsI3pInputLine3Cur OBJECT-TYPE
	SYNTAX INTEGER
	ACCESS read-only
	STATUS mandatory
	DESCRIPTION
		"The current UPS Input Line3 Current in 1/100 A"
	::= { upsI3pAnalog 44 }

upsI3pInputLine3Power OBJECT-TYPE
	SYNTAX INTEGER
	ACCESS read-only
	STATUS mandatory
	DESCRIPTION
		"The current UPS Input Line3 Power in 1/100 KW"
	::= { upsI3pAnalog 45 }

upsI3pOutputSource OBJECT-TYPE
	SYNTAX INTEGER {
		Normal(0),
		ByBattery(100),
		ByPass(200),
		Reduce(300),
		Boost(400),
		Other(500)
	}
	ACCESS read-only
	STATUS mandatory
	DESCRIPTION
		"The current UPS Output Source"
	::= { upsI3pAnalog 46 }

upsI3pOutputFre OBJECT-TYPE
	SYNTAX INTEGER
	ACCESS read-only
	STATUS mandatory
	DESCRIPTION
		"The current UPS Output Fre in 1/100 HZ"
	::= { upsI3pAnalog 47 }

upsI3pOutputLines OBJECT-TYPE
	SYNTAX INTEGER
	ACCESS read-only
	STATUS mandatory
	DESCRIPTION
		"The current UPS Output Lines in 1/100"
	::= { upsI3pAnalog 48 }

upsI3pOutputLine1Vol OBJECT-TYPE
	SYNTAX INTEGER
	ACCESS read-only
	STATUS mandatory
	DESCRIPTION
		"The current UPS Output Line1 voltage in 1/100 V"
	::= { upsI3pAnalog 49 }

upsI3pOutputLine1Cur OBJECT-TYPE
	SYNTAX INTEGER
	ACCESS read-only
	STATUS mandatory
	DESCRIPTION
		"The current UPS Output Line1 Current in 1/100 A"
	::= { upsI3pAnalog 50 }

upsI3pOutputLine1Power OBJECT-TYPE
	SYNTAX INTEGER
	ACCESS read-only
	STATUS mandatory
	DESCRIPTION
		"The current UPS Output Line1 Power in 1/100 KW"
	::= { upsI3pAnalog 51 }

upsI3pOutputLine1Load OBJECT-TYPE
	SYNTAX INTEGER
	ACCESS read-only
	STATUS mandatory
	DESCRIPTION
		"The current UPS Output Line1 Load in 1/100 %"
	::= { upsI3pAnalog 52 }

upsI3pOutputLine2Vol OBJECT-TYPE
	SYNTAX INTEGER
	ACCESS read-only
	STATUS mandatory
	DESCRIPTION
		"The current UPS Output Line2 voltage in 1/100 V"
	::= { upsI3pAnalog 53 }

upsI3pOutputLine2Cur OBJECT-TYPE
	SYNTAX INTEGER
	ACCESS read-only
	STATUS mandatory
	DESCRIPTION
		"The current UPS Output Line2 Current in 1/100 A"
	::= { upsI3pAnalog 54 }

upsI3pOutputLine2Power OBJECT-TYPE
	SYNTAX INTEGER
	ACCESS read-only
	STATUS mandatory
	DESCRIPTION
		"The current UPS Output Line2 Power in 1/100 KW"
	::= { upsI3pAnalog 55 }

upsI3pOutputLine2Load OBJECT-TYPE
	SYNTAX INTEGER
	ACCESS read-only
	STATUS mandatory
	DESCRIPTION
		"The current UPS Output Line2 Load in 1/100 %"
	::= { upsI3pAnalog 56 }

upsI3pOutputLine3Vol OBJECT-TYPE
	SYNTAX INTEGER
	ACCESS read-only
	STATUS mandatory
	DESCRIPTION
		"The current UPS Output Line3 voltage in 1/100 V"
	::= { upsI3pAnalog 57 }

upsI3pOutputLine3Cur OBJECT-TYPE
	SYNTAX INTEGER
	ACCESS read-only
	STATUS mandatory
	DESCRIPTION
		"The current UPS Output Line3 Current in 1/100 A"
	::= { upsI3pAnalog 58 }

upsI3pOutputLine3Power OBJECT-TYPE
	SYNTAX INTEGER
	ACCESS read-only
	STATUS mandatory
	DESCRIPTION
		"The current UPS Output Line3 Power in 1/100 KW"
	::= { upsI3pAnalog 59 }

upsI3pOutputLine3Load OBJECT-TYPE
	SYNTAX INTEGER
	ACCESS read-only
	STATUS mandatory
	DESCRIPTION
		"The current UPS Output Line3 Load in 1/100 %"
	::= { upsI3pAnalog 60 }

upsI3pBypassFre OBJECT-TYPE
	SYNTAX INTEGER
	ACCESS read-only
	STATUS mandatory
	DESCRIPTION
		"The current UPS Bypass Fre in 1/100 HZ"
	::= { upsI3pAnalog 61 }

upsI3pBypassLines OBJECT-TYPE
	SYNTAX INTEGER
	ACCESS read-only
	STATUS mandatory
	DESCRIPTION
		"The current UPS Bypass Lines in 1/100"
	::= { upsI3pAnalog 62 }

upsI3pBypassLine1Vol OBJECT-TYPE
	SYNTAX INTEGER
	ACCESS read-only
	STATUS mandatory
	DESCRIPTION
		"The current UPS Bypass Line1 voltage in 1/100 V"
	::= { upsI3pAnalog 63 }

upsI3pBypassLine1Cur OBJECT-TYPE
	SYNTAX INTEGER
	ACCESS read-only
	STATUS mandatory
	DESCRIPTION
		"The current UPS Bypass Line1 Current in 1/100 A"
	::= { upsI3pAnalog 64 }

upsI3pBypassLine1Power OBJECT-TYPE
	SYNTAX INTEGER
	ACCESS read-only
	STATUS mandatory
	DESCRIPTION
		"The current UPS Bypass Line1 Power in 1/100 W"
	::= { upsI3pAnalog 65 }

upsI3pBypassLine2Vol OBJECT-TYPE
	SYNTAX INTEGER
	ACCESS read-only
	STATUS mandatory
	DESCRIPTION
		"The current UPS Bypass Line2 voltage in 1/100 V"
	::= { upsI3pAnalog 66 }

upsI3pBypassLine2Cur OBJECT-TYPE
	SYNTAX INTEGER
	ACCESS read-only
	STATUS mandatory
	DESCRIPTION
		"The current UPS Bypass Line2 Current in 1/100 A"
	::= { upsI3pAnalog 67 }

upsI3pBypassLine2Power OBJECT-TYPE
	SYNTAX INTEGER
	ACCESS read-only
	STATUS mandatory
	DESCRIPTION
		"The current UPS Bypass Line2 Power in 1/100 W"
	::= { upsI3pAnalog 68 }

upsI3pBypassLine3Vol OBJECT-TYPE
	SYNTAX INTEGER
	ACCESS read-only
	STATUS mandatory
	DESCRIPTION
		"The current UPS Bypass Line3 voltage in 1/100 V"
	::= { upsI3pAnalog 69 }

upsI3pBypassLine3Cur OBJECT-TYPE
	SYNTAX INTEGER
	ACCESS read-only
	STATUS mandatory
	DESCRIPTION
		"The current UPS Bypass Line3 Current in 1/100 A"
	::= { upsI3pAnalog 70 }

upsI3pBypassLine3Power OBJECT-TYPE
	SYNTAX INTEGER
	ACCESS read-only
	STATUS mandatory
	DESCRIPTION
		"The current UPS Bypass Line3 Power in 1/100 W"
	::= { upsI3pAnalog 71 }

upsI3pTestResult OBJECT-TYPE
	SYNTAX INTEGER {
		NoTest(0),
		TestPass(100),
		TestInProgress(200),
		GeneralTestFail(300),
		BatteryTestFail(400),
		DeepBatteryTestFail(500)
	}
	ACCESS read-only
	STATUS mandatory
	DESCRIPTION
		"The current UPS Test result"
	::= { upsI3pAnalog 72 }

upsI3pOutputTotalPower OBJECT-TYPE
	SYNTAX INTEGER
	ACCESS read-only
	STATUS mandatory
	DESCRIPTION
		"The current UPS output Total Power in 1/100 W"
	::= { upsI3pAnalog 73 }

upsI3pBatteryCap OBJECT-TYPE
	SYNTAX INTEGER
	ACCESS read-only
	STATUS mandatory
	DESCRIPTION
		"The current UPS Temperature in 1/100 C"
	::= { upsI3pAnalog 74 }

upsI3pTemperature OBJECT-TYPE
	SYNTAX INTEGER
	ACCESS read-only
	STATUS mandatory
	DESCRIPTION
		"The current UPS Fault ID in 1/100"
	::= { upsI3pAnalog 75 }

-- the upsI3pSwitch group
upsI3pTemperatureTooHigh OBJECT-TYPE
	SYNTAX INTEGER  {
		normal(0),
		occur(1)
	}
	ACCESS read-only
	STATUS mandatory
	DESCRIPTION
		"Temperature too High!"
	::= { upsI3pSwitch 17 }

upsI3pInputFault OBJECT-TYPE
	SYNTAX INTEGER  {
		normal(0),
		occur(1)
	}
	ACCESS read-only
	STATUS mandatory
	DESCRIPTION
		"Input Fault!"
	::= { upsI3pSwitch 18 }

upsI3pOutputFault OBJECT-TYPE
	SYNTAX INTEGER  {
		normal(0),
		occur(1)
	}
	ACCESS read-only
	STATUS mandatory
	DESCRIPTION
		"Output Fault!"
	::= { upsI3pSwitch 19 }

upsI3pOverLoad OBJECT-TYPE
	SYNTAX INTEGER  {
		normal(0),
		occur(1)
	}
	ACCESS read-only
	STATUS mandatory
	DESCRIPTION
		"Over Load!"
	::= { upsI3pSwitch 20 }

upsI3pBypassFault OBJECT-TYPE
	SYNTAX INTEGER  {
		normal(0),
		occur(1)
	}
	ACCESS read-only
	STATUS mandatory
	DESCRIPTION
		"Bapass Fault!"
	::= { upsI3pSwitch 21 }

upsI3pOutputShutdown OBJECT-TYPE
	SYNTAX INTEGER  {
		normal(0),
		occur(1)
	}
	ACCESS read-only
	STATUS mandatory
	DESCRIPTION
		"Output Shutdown"
	::= { upsI3pSwitch 22 }

upsI3pShutdown OBJECT-TYPE
	SYNTAX INTEGER  {
		normal(0),
		occur(1)
	}
	ACCESS read-only
	STATUS mandatory
	DESCRIPTION
		"UPS Shutdown!"
	::= { upsI3pSwitch 23 }

upsI3pChargeFault OBJECT-TYPE
	SYNTAX INTEGER  {
		normal(0),
		occur(1)
	}
	ACCESS read-only
	STATUS mandatory
	DESCRIPTION
		"Battery charge Fault!"
	::= { upsI3pSwitch 24 }

upsI3pSystemShutdown OBJECT-TYPE
	SYNTAX INTEGER  {
		normal(0),
		occur(1)
	}
	ACCESS read-only
	STATUS mandatory
	DESCRIPTION
		"System Shutdown!"
	::= { upsI3pSwitch 25 }

upsI3pFanFault OBJECT-TYPE
	SYNTAX INTEGER  {
		normal(0),
		occur(1)
	}
	ACCESS read-only
	STATUS mandatory
	DESCRIPTION
		"Fan Fault!"
	::= { upsI3pSwitch 26 }

upsI3pFuseFault OBJECT-TYPE
	SYNTAX INTEGER  {
		normal(0),
		occur(1)
	}
	ACCESS read-only
	STATUS mandatory
	DESCRIPTION
		"Fuse Fault!"
	::= { upsI3pSwitch 27 }

upsI3pGeneralFault OBJECT-TYPE
	SYNTAX INTEGER  {
		normal(0),
		occur(1)
	}
	ACCESS read-only
	STATUS mandatory
	DESCRIPTION
		"Gereral Fault!"
	::= { upsI3pSwitch 28 }

upsI3pAutoRestart OBJECT-TYPE
	SYNTAX INTEGER  {
		normal(0),
		occur(1)
	}
	ACCESS read-only
	STATUS mandatory
	DESCRIPTION
		"automatic Restart!"
	::= { upsI3pSwitch 29 }

upsI3pShutdownDelayStatus OBJECT-TYPE
	SYNTAX INTEGER  {
		normal(0),
		occur(1)
	}
	ACCESS read-only
	STATUS mandatory
	DESCRIPTION
		"Shutdown delay!"
	::= { upsI3pSwitch 30 }

upsI3pShutdownAtonce OBJECT-TYPE
	SYNTAX INTEGER  {
		normal(0),
		occur(1)
	}
	ACCESS read-only
	STATUS mandatory
	DESCRIPTION
		"Shutdown at once!"
	::= { upsI3pSwitch 31 }

usp1Communication OBJECT-TYPE
	SYNTAX INTEGER  {
		normal(0),
		occur(1)
	}
	ACCESS read-only
	STATUS mandatory
	DESCRIPTION
		"Communication status!"
	::= { upsI3pSwitch 32 }

upsI3pBatteryFault OBJECT-TYPE
	SYNTAX INTEGER  {
		normal(0),
		occur(1)
	}
	ACCESS read-only
	STATUS mandatory
	DESCRIPTION
		"battery Fault!"
	::= { upsI3pSwitch 33 }

upsI3pBatteryVolLow OBJECT-TYPE
	SYNTAX INTEGER  {
		normal(0),
		occur(1)
	}
	ACCESS read-only
	STATUS mandatory
	DESCRIPTION
		"battery voltage too low!"
	::= { upsI3pSwitch 34 }

upsI3pBypass OBJECT-TYPE
	SYNTAX INTEGER  {
		normal(0),
		occur(1)
	}
	ACCESS read-only
	STATUS mandatory
	DESCRIPTION
		"Bypass!"
	::= { upsI3pSwitch 35 }

upsI3pOtherFault OBJECT-TYPE
	SYNTAX INTEGER  {
		normal(0),
		occur(1)
	}
	ACCESS read-only
	STATUS mandatory
	DESCRIPTION
		"Other Fault!"
	::= { upsI3pSwitch 36 }

upsI3pTestInProgress OBJECT-TYPE
	SYNTAX INTEGER  {
		normal(0),
		occur(1)
	}
	ACCESS read-only
	STATUS mandatory
	DESCRIPTION
		"Now Testing!"
	::= { upsI3pSwitch 37 } 
	
upsI3pRectifierFailure OBJECT-TYPE
	SYNTAX INTEGER  {
		normal(0),
		occur(1)
	}
	ACCESS read-only
	STATUS mandatory
	DESCRIPTION
		"Rectifier Failure!"
	::= { upsI3pSwitch 100 }

upsI3pInverterFailure OBJECT-TYPE
	SYNTAX INTEGER  {
		normal(0),
		occur(1)
	}
	ACCESS read-only
	STATUS mandatory
	DESCRIPTION
		"Inverter Failure!"
	::= { upsI3pSwitch 101 }

-- the upsI3pControl group
upsI3pTest OBJECT-TYPE
	SYNTAX INTEGER 
	ACCESS read-write
	STATUS mandatory
	DESCRIPTION
		"0:cancle test; -1:Test till battery voltage low; other:test Some Time"
	::= { upsI3pControl 1 }

upsI3pShutdownDelay OBJECT-TYPE
	SYNTAX INTEGER 
	ACCESS read-write
	STATUS mandatory
	DESCRIPTION
		"0:cancle shutdown; other:Shutdown ups after delay UNIT:second"
	::= { upsI3pControl 2 }

upsI3pRestartDelay OBJECT-TYPE
	SYNTAX INTEGER 
	ACCESS read-write
	STATUS mandatory
	DESCRIPTION
		"Restart ups after delay UNIT:second"
	::= { upsI3pControl 3 }

-- the upsIII3ppStrInfo group
upsI3pManufacturer  OBJECT-TYPE
	SYNTAX DisplayString
	ACCESS read-only
	STATUS mandatory
	DESCRIPTION
		"The UPS Manufacturer name (e.g. 'richcomm')."
	::= { upsI3pStrInfo 1 }

upsI3pModel  OBJECT-TYPE
	SYNTAX DisplayString
	ACCESS read-only
	STATUS mandatory
	DESCRIPTION
		"The UPS Model name (e.g. 'RC-600VA')."
	::= { upsI3pStrInfo 2 }

upsI3pVersion OBJECT-TYPE
	SYNTAX DisplayString
	ACCESS read-only
	STATUS mandatory
	DESCRIPTION
		"The firmware revision of the UPS system"
	::= { upsI3pStrInfo 3 }

upsI3pRateInputVol OBJECT-TYPE
	SYNTAX INTEGER
	UNITS     "0.01 V"
	ACCESS read-only
	STATUS mandatory
	DESCRIPTION
		"The Rate Input voltage of the UPS system"
	::= { upsI3pStrInfo 4 }

upsI3pRateCurrent OBJECT-TYPE
	SYNTAX INTEGER
	UNITS     "0.01 A"
	ACCESS read-only
	STATUS mandatory
	DESCRIPTION
		"The Rate Current of the UPS system"
	::= { upsI3pStrInfo 5 }

upsI3pRateBatVol OBJECT-TYPE
	SYNTAX INTEGER
	UNITS     "0.01 V"
	ACCESS read-only
	STATUS mandatory
	DESCRIPTION
		"The Rate battery voltage of the UPS system"
	::= { upsI3pStrInfo 6 }

upsI3pRateFre OBJECT-TYPE
	SYNTAX INTEGER
	UNITS     "0.01 Hz"
	ACCESS read-only
	STATUS mandatory
	DESCRIPTION
		"The Rate Frequency of the UPS system"
	::= { upsI3pStrInfo 7 }

-- ****************************upsII3p************************************ 
upsII3pAnalog                       OBJECT IDENTIFIER ::=  { upsII3p 1 }
upsII3pSwitch                       OBJECT IDENTIFIER ::=  { upsII3p 2 }
upsII3pControl                      OBJECT IDENTIFIER ::=  { upsII3p 3 }
upsII3pStrInfo                      OBJECT IDENTIFIER ::=  { upsII3p 4 }
-- the upsII3pAnalog group

upsII3pAutoRestartType OBJECT-TYPE
	SYNTAX INTEGER {
		automatic(0),
		manual(100)
	}
	ACCESS read-only
	STATUS mandatory
	DESCRIPTION
		"The current UPS automatic restart type"
	::= { upsII3pAnalog 21 }

upsII3pShutdownType OBJECT-TYPE
	SYNTAX INTEGER {
		shutdownOutputOnly(0),
		Entire(100)
	}
	ACCESS read-only
	STATUS mandatory
	DESCRIPTION
		"The current UPS shutdown type"
	::= { upsII3pAnalog 22 }

upsII3pBatCondition OBJECT-TYPE
	SYNTAX INTEGER {
		good(0),
		weak(100),
		replace(200)
	}
	ACCESS read-only
	STATUS mandatory
	DESCRIPTION
		"The current Battery Condition"
	::= { upsII3pAnalog 23 }

upsII3pBatStatus OBJECT-TYPE
	SYNTAX INTEGER {
		OK(0),
		Low(100),
		Depleted(200)
	}
	ACCESS read-only
	STATUS mandatory
	DESCRIPTION
		"The current Battery Status"
	::= { upsII3pAnalog 24 }

upsII3pBatChargeStatus OBJECT-TYPE
	SYNTAX INTEGER {
		floating(0),
		charging(100),
		resting(200),
		discharging(300)
	}
	ACCESS read-only
	STATUS mandatory
	DESCRIPTION
		"The current Battery Charge Status"
	::= { upsII3pAnalog 25 }

--upsII3pSecondOnBattery OBJECT-TYPE
--	SYNTAX INTEGER
--	ACCESS read-only
--	STATUS mandatory
--	DESCRIPTION
--		"The current UPS Senond On Battery in 1/100 Second"
--	::= { upsII3pAnalog 26 }

upsII3pEstimatedMinutesOnBat OBJECT-TYPE
	SYNTAX INTEGER
	ACCESS read-only
	STATUS mandatory
	DESCRIPTION
		"The current UPS estimated Minutes On Battery in 1/100 Minutes"
	::= { upsII3pAnalog 26 }

upsII3pEstimatedCharge OBJECT-TYPE
	SYNTAX INTEGER
	ACCESS read-only
	STATUS mandatory
	DESCRIPTION
		"The current UPS estimated Charge in 1/100 %"
	::= { upsII3pAnalog 28 }

upsII3pBatteryVol OBJECT-TYPE
	SYNTAX INTEGER
	ACCESS read-only
	STATUS mandatory
	DESCRIPTION
		"The current UPS Battery voltage in 1/100 V"
	::= { upsII3pAnalog 29 }

upsII3pBatteryCurrent OBJECT-TYPE
	SYNTAX INTEGER
	ACCESS read-only
	STATUS mandatory
	DESCRIPTION
		"The current UPS Battery Current in 1/100 A"
	::= { upsII3pAnalog 30 }

upsII3pBatteryTemperature OBJECT-TYPE
	SYNTAX INTEGER
	ACCESS read-only
	STATUS mandatory
	DESCRIPTION
		"The current UPS Battery Temperature in 1/100 C"
	::= { upsII3pAnalog 31 }

upsII3pInputLineBads OBJECT-TYPE
	SYNTAX INTEGER
	ACCESS read-only
	STATUS mandatory
	DESCRIPTION
		"The current UPS Input line bads in 1/100 line"
	::= { upsII3pAnalog 32 }

upsII3pInputLines OBJECT-TYPE
	SYNTAX INTEGER
	ACCESS read-only
	STATUS mandatory
	DESCRIPTION
		"The current UPS Input line in 1/100 line"
	::= { upsII3pAnalog 33 }

upsII3pInputLine1Fre OBJECT-TYPE
	SYNTAX INTEGER
	ACCESS read-only
	STATUS mandatory
	DESCRIPTION
		"The current UPS Input Line1 Fre in 1/100 Hz"
	::= { upsII3pAnalog 34 }

upsII3pInputLine1Vol OBJECT-TYPE
	SYNTAX INTEGER
	ACCESS read-only
	STATUS mandatory
	DESCRIPTION
		"The current UPS Input Line1 voltage in 1/100 V"
	::= { upsII3pAnalog 35 }

upsII3pInputLine1Cur OBJECT-TYPE
	SYNTAX INTEGER
	ACCESS read-only
	STATUS mandatory
	DESCRIPTION
		"The current UPS Input Line1 Current in 1/100 A"
	::= { upsII3pAnalog 36 }

upsII3pInputLine1Power OBJECT-TYPE
	SYNTAX INTEGER
	ACCESS read-only
	STATUS mandatory
	DESCRIPTION
		"The current UPS Input Line1 Power in 1/100 KW"
	::= { upsII3pAnalog 37 }

upsII3pInputLine2Fre OBJECT-TYPE
	SYNTAX INTEGER
	ACCESS read-only
	STATUS mandatory
	DESCRIPTION
		"The current UPS Input Line2 Fre in 1/100 Hz"
	::= { upsII3pAnalog 38 }

upsII3pInputLine2Vol OBJECT-TYPE
	SYNTAX INTEGER
	ACCESS read-only
	STATUS mandatory
	DESCRIPTION
		"The current UPS Input Line2 voltage in 1/100 V"
	::= { upsII3pAnalog 39 }

upsII3pInputLine2Cur OBJECT-TYPE
	SYNTAX INTEGER
	ACCESS read-only
	STATUS mandatory
	DESCRIPTION
		"The current UPS Input Line2 Current in 1/100 A"
	::= { upsII3pAnalog 40 }

upsII3pInputLine2Power OBJECT-TYPE
	SYNTAX INTEGER
	ACCESS read-only
	STATUS mandatory
	DESCRIPTION
		"The current UPS Input Line2 Power in 1/100 KW"
	::= { upsII3pAnalog 41 }

upsII3pInputLine3Fre OBJECT-TYPE
	SYNTAX INTEGER
	ACCESS read-only
	STATUS mandatory
	DESCRIPTION
		"The current UPS Input Line3 Fre in 1/100 Hz"
	::= { upsII3pAnalog 42 }

upsII3pInputLine3Vol OBJECT-TYPE
	SYNTAX INTEGER
	ACCESS read-only
	STATUS mandatory
	DESCRIPTION
		"The current UPS Input Line3 voltage in 1/100 V"
	::= { upsII3pAnalog 43 }

upsII3pInputLine3Cur OBJECT-TYPE
	SYNTAX INTEGER
	ACCESS read-only
	STATUS mandatory
	DESCRIPTION
		"The current UPS Input Line3 Current in 1/100 A"
	::= { upsII3pAnalog 44 }

upsII3pInputLine3Power OBJECT-TYPE
	SYNTAX INTEGER
	ACCESS read-only
	STATUS mandatory
	DESCRIPTION
		"The current UPS Input Line3 Power in 1/100 KW"
	::= { upsII3pAnalog 45 }

upsII3pOutputSource OBJECT-TYPE
	SYNTAX INTEGER {
		Normal(0),
		ByBattery(100),
		ByPass(200),
		Reduce(300),
		Boost(400),
		Other(500)
	}
	ACCESS read-only
	STATUS mandatory
	DESCRIPTION
		"The current UPS Output Source"
	::= { upsII3pAnalog 46 }

upsII3pOutputFre OBJECT-TYPE
	SYNTAX INTEGER
	ACCESS read-only
	STATUS mandatory
	DESCRIPTION
		"The current UPS Output Fre in 1/100 HZ"
	::= { upsII3pAnalog 47 }

upsII3pOutputLines OBJECT-TYPE
	SYNTAX INTEGER
	ACCESS read-only
	STATUS mandatory
	DESCRIPTION
		"The current UPS Output Lines in 1/100"
	::= { upsII3pAnalog 48 }

upsII3pOutputLine1Vol OBJECT-TYPE
	SYNTAX INTEGER
	ACCESS read-only
	STATUS mandatory
	DESCRIPTION
		"The current UPS Output Line1 voltage in 1/100 V"
	::= { upsII3pAnalog 49 }

upsII3pOutputLine1Cur OBJECT-TYPE
	SYNTAX INTEGER
	ACCESS read-only
	STATUS mandatory
	DESCRIPTION
		"The current UPS Output Line1 Current in 1/100 A"
	::= { upsII3pAnalog 50 }

upsII3pOutputLine1Power OBJECT-TYPE
	SYNTAX INTEGER
	ACCESS read-only
	STATUS mandatory
	DESCRIPTION
		"The current UPS Output Line1 Power in 1/100 KW"
	::= { upsII3pAnalog 51 }

upsII3pOutputLine1Load OBJECT-TYPE
	SYNTAX INTEGER
	ACCESS read-only
	STATUS mandatory
	DESCRIPTION
		"The current UPS Output Line1 Load in 1/100 %"
	::= { upsII3pAnalog 52 }

upsII3pOutputLine2Vol OBJECT-TYPE
	SYNTAX INTEGER
	ACCESS read-only
	STATUS mandatory
	DESCRIPTION
		"The current UPS Output Line2 voltage in 1/100 V"
	::= { upsII3pAnalog 53 }

upsII3pOutputLine2Cur OBJECT-TYPE
	SYNTAX INTEGER
	ACCESS read-only
	STATUS mandatory
	DESCRIPTION
		"The current UPS Output Line2 Current in 1/100 A"
	::= { upsII3pAnalog 54 }

upsII3pOutputLine2Power OBJECT-TYPE
	SYNTAX INTEGER
	ACCESS read-only
	STATUS mandatory
	DESCRIPTION
		"The current UPS Output Line2 Power in 1/100 KW"
	::= { upsII3pAnalog 55 }

upsII3pOutputLine2Load OBJECT-TYPE
	SYNTAX INTEGER
	ACCESS read-only
	STATUS mandatory
	DESCRIPTION
		"The current UPS Output Line2 Load in 1/100 %"
	::= { upsII3pAnalog 56 }

upsII3pOutputLine3Vol OBJECT-TYPE
	SYNTAX INTEGER
	ACCESS read-only
	STATUS mandatory
	DESCRIPTION
		"The current UPS Output Line3 voltage in 1/100 V"
	::= { upsII3pAnalog 57 }

upsII3pOutputLine3Cur OBJECT-TYPE
	SYNTAX INTEGER
	ACCESS read-only
	STATUS mandatory
	DESCRIPTION
		"The current UPS Output Line3 Current in 1/100 A"
	::= { upsII3pAnalog 58 }

upsII3pOutputLine3Power OBJECT-TYPE
	SYNTAX INTEGER
	ACCESS read-only
	STATUS mandatory
	DESCRIPTION
		"The current UPS Output Line3 Power in 1/100 KW"
	::= { upsII3pAnalog 59 }

upsII3pOutputLine3Load OBJECT-TYPE
	SYNTAX INTEGER
	ACCESS read-only
	STATUS mandatory
	DESCRIPTION
		"The current UPS Output Line3 Load in 1/100 %"
	::= { upsII3pAnalog 60 }

upsII3pBypassFre OBJECT-TYPE
	SYNTAX INTEGER
	ACCESS read-only
	STATUS mandatory
	DESCRIPTION
		"The current UPS Bypass Fre in 1/100 HZ"
	::= { upsII3pAnalog 61 }

upsII3pBypassLines OBJECT-TYPE
	SYNTAX INTEGER
	ACCESS read-only
	STATUS mandatory
	DESCRIPTION
		"The current UPS Bypass Lines in 1/100"
	::= { upsII3pAnalog 62 }

upsII3pBypassLine1Vol OBJECT-TYPE
	SYNTAX INTEGER
	ACCESS read-only
	STATUS mandatory
	DESCRIPTION
		"The current UPS Bypass Line1 voltage in 1/100 V"
	::= { upsII3pAnalog 63 }

upsII3pBypassLine1Cur OBJECT-TYPE
	SYNTAX INTEGER
	ACCESS read-only
	STATUS mandatory
	DESCRIPTION
		"The current UPS Bypass Line1 Current in 1/100 A"
	::= { upsII3pAnalog 64 }

upsII3pBypassLine1Power OBJECT-TYPE
	SYNTAX INTEGER
	ACCESS read-only
	STATUS mandatory
	DESCRIPTION
		"The current UPS Bypass Line1 Power in 1/100 W"
	::= { upsII3pAnalog 65 }

upsII3pBypassLine2Vol OBJECT-TYPE
	SYNTAX INTEGER
	ACCESS read-only
	STATUS mandatory
	DESCRIPTION
		"The current UPS Bypass Line2 voltage in 1/100 V"
	::= { upsII3pAnalog 66 }

upsII3pBypassLine2Cur OBJECT-TYPE
	SYNTAX INTEGER
	ACCESS read-only
	STATUS mandatory
	DESCRIPTION
		"The current UPS Bypass Line2 Current in 1/100 A"
	::= { upsII3pAnalog 67 }

upsII3pBypassLine2Power OBJECT-TYPE
	SYNTAX INTEGER
	ACCESS read-only
	STATUS mandatory
	DESCRIPTION
		"The current UPS Bypass Line2 Power in 1/100 W"
	::= { upsII3pAnalog 68 }

upsII3pBypassLine3Vol OBJECT-TYPE
	SYNTAX INTEGER
	ACCESS read-only
	STATUS mandatory
	DESCRIPTION
		"The current UPS Bypass Line3 voltage in 1/100 V"
	::= { upsII3pAnalog 69 }

upsII3pBypassLine3Cur OBJECT-TYPE
	SYNTAX INTEGER
	ACCESS read-only
	STATUS mandatory
	DESCRIPTION
		"The current UPS Bypass Line3 Current in 1/100 A"
	::= { upsII3pAnalog 70 }

upsII3pBypassLine3Power OBJECT-TYPE
	SYNTAX INTEGER
	ACCESS read-only
	STATUS mandatory
	DESCRIPTION
		"The current UPS Bypass Line3 Power in 1/100 W"
	::= { upsII3pAnalog 71 }

upsII3pTestResult OBJECT-TYPE
	SYNTAX INTEGER {
		NoTest(0),
		TestPass(100),
		TestInProgress(200),
		GeneralTestFail(300),
		BatteryTestFail(400),
		DeepBatteryTestFail(500)
	}
	ACCESS read-only
	STATUS mandatory
	DESCRIPTION
		"The current UPS Test result"
	::= { upsII3pAnalog 72 }

upsII3pOutputTotalPower OBJECT-TYPE
	SYNTAX INTEGER
	ACCESS read-only
	STATUS mandatory
	DESCRIPTION
		"The current UPS output Total Power in 1/100 W"
	::= { upsII3pAnalog 73 }

upsII3pBatteryCap OBJECT-TYPE
	SYNTAX INTEGER
	ACCESS read-only
	STATUS mandatory
	DESCRIPTION
		"The current UPS Temperature in 1/100 C"
	::= { upsII3pAnalog 74 }

upsII3pTemperature OBJECT-TYPE
	SYNTAX INTEGER
	ACCESS read-only
	STATUS mandatory
	DESCRIPTION
		"The current UPS Fault ID in 1/100"
	::= { upsII3pAnalog 75 }

-- the upsII3pSwitch group
upsII3pTemperatureTooHigh OBJECT-TYPE
	SYNTAX INTEGER  {
		normal(0),
		occur(1)
	}
	ACCESS read-only
	STATUS mandatory
	DESCRIPTION
		"Temperature too High!"
	::= { upsII3pSwitch 17 }

upsII3pInputFault OBJECT-TYPE
	SYNTAX INTEGER  {
		normal(0),
		occur(1)
	}
	ACCESS read-only
	STATUS mandatory
	DESCRIPTION
		"Input Fault!"
	::= { upsII3pSwitch 18 }

upsII3pOutputFault OBJECT-TYPE
	SYNTAX INTEGER  {
		normal(0),
		occur(1)
	}
	ACCESS read-only
	STATUS mandatory
	DESCRIPTION
		"Output Fault!"
	::= { upsII3pSwitch 19 }

upsII3pOverLoad OBJECT-TYPE
	SYNTAX INTEGER  {
		normal(0),
		occur(1)
	}
	ACCESS read-only
	STATUS mandatory
	DESCRIPTION
		"Over Load!"
	::= { upsII3pSwitch 20 }

upsII3pBypassFault OBJECT-TYPE
	SYNTAX INTEGER  {
		normal(0),
		occur(1)
	}
	ACCESS read-only
	STATUS mandatory
	DESCRIPTION
		"Bapass Fault!"
	::= { upsII3pSwitch 21 }

upsII3pOutputShutdown OBJECT-TYPE
	SYNTAX INTEGER  {
		normal(0),
		occur(1)
	}
	ACCESS read-only
	STATUS mandatory
	DESCRIPTION
		"Output Shutdown"
	::= { upsII3pSwitch 22 }

upsII3pShutdown OBJECT-TYPE
	SYNTAX INTEGER  {
		normal(0),
		occur(1)
	}
	ACCESS read-only
	STATUS mandatory
	DESCRIPTION
		"UPS Shutdown!"
	::= { upsII3pSwitch 23 }

upsII3pChargeFault OBJECT-TYPE
	SYNTAX INTEGER  {
		normal(0),
		occur(1)
	}
	ACCESS read-only
	STATUS mandatory
	DESCRIPTION
		"Battery charge Fault!"
	::= { upsII3pSwitch 24 }

upsII3pSystemShutdown OBJECT-TYPE
	SYNTAX INTEGER  {
		normal(0),
		occur(1)
	}
	ACCESS read-only
	STATUS mandatory
	DESCRIPTION
		"System Shutdown!"
	::= { upsII3pSwitch 25 }

upsII3pFanFault OBJECT-TYPE
	SYNTAX INTEGER  {
		normal(0),
		occur(1)
	}
	ACCESS read-only
	STATUS mandatory
	DESCRIPTION
		"Fan Fault!"
	::= { upsII3pSwitch 26 }

upsII3pFuseFault OBJECT-TYPE
	SYNTAX INTEGER  {
		normal(0),
		occur(1)
	}
	ACCESS read-only
	STATUS mandatory
	DESCRIPTION
		"Fuse Fault!"
	::= { upsII3pSwitch 27 }

upsII3pGeneralFault OBJECT-TYPE
	SYNTAX INTEGER  {
		normal(0),
		occur(1)
	}
	ACCESS read-only
	STATUS mandatory
	DESCRIPTION
		"Gereral Fault!"
	::= { upsII3pSwitch 28 }

upsII3pAutoRestart OBJECT-TYPE
	SYNTAX INTEGER  {
		normal(0),
		occur(1)
	}
	ACCESS read-only
	STATUS mandatory
	DESCRIPTION
		"automatic Restart!"
	::= { upsII3pSwitch 29 }

upsII3pShutdownDelayStatus OBJECT-TYPE
	SYNTAX INTEGER  {
		normal(0),
		occur(1)
	}
	ACCESS read-only
	STATUS mandatory
	DESCRIPTION
		"Shutdown delay!"
	::= { upsII3pSwitch 30 }

upsII3pShutdownAtonce OBJECT-TYPE
	SYNTAX INTEGER  {
		normal(0),
		occur(1)
	}
	ACCESS read-only
	STATUS mandatory
	DESCRIPTION
		"Shutdown at once!"
	::= { upsII3pSwitch 31 }

usp2Communication OBJECT-TYPE
	SYNTAX INTEGER  {
		normal(0),
		occur(1)
	}
	ACCESS read-only
	STATUS mandatory
	DESCRIPTION
		"Communication status!"
	::= { upsII3pSwitch 32 }

upsII3pBatteryFault OBJECT-TYPE
	SYNTAX INTEGER  {
		normal(0),
		occur(1)
	}
	ACCESS read-only
	STATUS mandatory
	DESCRIPTION
		"battery Fault!"
	::= { upsII3pSwitch 33 }

upsII3pBatteryVolLow OBJECT-TYPE
	SYNTAX INTEGER  {
		normal(0),
		occur(1)
	}
	ACCESS read-only
	STATUS mandatory
	DESCRIPTION
		"battery voltage too low!"
	::= { upsII3pSwitch 34 }

upsII3pBypass OBJECT-TYPE
	SYNTAX INTEGER  {
		normal(0),
		occur(1)
	}
	ACCESS read-only
	STATUS mandatory
	DESCRIPTION
		"Bypass!"
	::= { upsII3pSwitch 35 }

upsII3pOtherFault OBJECT-TYPE
	SYNTAX INTEGER  {
		normal(0),
		occur(1)
	}
	ACCESS read-only
	STATUS mandatory
	DESCRIPTION
		"Other Fault!"
	::= { upsII3pSwitch 36 }

upsII3pTestInProgress OBJECT-TYPE
	SYNTAX INTEGER  {
		normal(0),
		occur(1)
	}
	ACCESS read-only
	STATUS mandatory
	DESCRIPTION
		"Now Testing!"
	::= { upsII3pSwitch 37 }

upsII3pRectifierFailure OBJECT-TYPE
	SYNTAX INTEGER  {
		normal(0),
		occur(1)
	}
	ACCESS read-only
	STATUS mandatory
	DESCRIPTION
		"Rectifier Failure!"
	::= { upsII3pSwitch 100 }

upsII3pInverterFailure OBJECT-TYPE
	SYNTAX INTEGER  {
		normal(0),
		occur(1)
	}
	ACCESS read-only
	STATUS mandatory
	DESCRIPTION
		"Inverter Failure!"
	::= { upsII3pSwitch 101 }  
	
-- the upsII3pControl group
upsII3pTest OBJECT-TYPE
	SYNTAX INTEGER 
	ACCESS read-write
	STATUS mandatory
	DESCRIPTION
		"0:cancle test; -1:Test till battery voltage low; other:test Some Time"
	::= { upsII3pControl 1 }

upsII3pShutdownDelay OBJECT-TYPE
	SYNTAX INTEGER 
	ACCESS read-write
	STATUS mandatory
	DESCRIPTION
		"0:cancle shutdown; other:Shutdown ups after delay UNIT:second"
	::= { upsII3pControl 2 }

upsII3pRestartDelay OBJECT-TYPE
	SYNTAX INTEGER 
	ACCESS read-write
	STATUS mandatory
	DESCRIPTION
		"Restart ups after delay UNIT:second"
	::= { upsII3pControl 3 }

-- the upsII3pStrInfo group
upsII3pManufacturer  OBJECT-TYPE
	SYNTAX DisplayString
	ACCESS read-only
	STATUS mandatory
	DESCRIPTION
		"The UPS Manufacturer name (e.g. 'richcomm')."
	::= { upsII3pStrInfo 1 }

upsII3pModel  OBJECT-TYPE
	SYNTAX DisplayString
	ACCESS read-only
	STATUS mandatory
	DESCRIPTION
		"The UPS Model name (e.g. 'RC-600VA')."
	::= { upsII3pStrInfo 2 }

upsII3pVersion OBJECT-TYPE
	SYNTAX DisplayString
	ACCESS read-only
	STATUS mandatory
	DESCRIPTION
		"The firmware revision of the UPS system"
	::= { upsII3pStrInfo 3 }

upsII3pRateInputVol OBJECT-TYPE
	SYNTAX INTEGER
	UNITS     "0.01 V"
	ACCESS read-only
	STATUS mandatory
	DESCRIPTION
		"The Rate Input voltage of the UPS system"
	::= { upsII3pStrInfo 4 }

upsII3pRateCurrent OBJECT-TYPE
	SYNTAX INTEGER
	UNITS     "0.01 A"
	ACCESS read-only
	STATUS mandatory
	DESCRIPTION
		"The Rate Current of the UPS system"
	::= { upsII3pStrInfo 5 }

upsII3pRateBatVol OBJECT-TYPE
	SYNTAX INTEGER
	UNITS     "0.01 V"
	ACCESS read-only
	STATUS mandatory
	DESCRIPTION
		"The Rate battery voltage of the UPS system"
	::= { upsII3pStrInfo 6 }

upsII3pRateFre OBJECT-TYPE
	SYNTAX INTEGER
	UNITS     "0.01 Hz"
	ACCESS read-only
	STATUS mandatory
	DESCRIPTION
		"The Rate Frequency of the UPS system"
	::= { upsII3pStrInfo 7 }
	
-- ****************************upsIII3p************************************ 
upsIII3pAnalog                       OBJECT IDENTIFIER ::=  { upsIII3p 1 }
upsIII3pSwitch                       OBJECT IDENTIFIER ::=  { upsIII3p 2 }
upsIII3pControl                      OBJECT IDENTIFIER ::=  { upsIII3p 3 }
upsIII3pStrInfo                      OBJECT IDENTIFIER ::=  { upsIII3p 4 }
-- the upsIII3pAnalog group

upsIII3pAutoRestartType OBJECT-TYPE
	SYNTAX INTEGER {
		automatic(0),
		manual(100)
	}
	ACCESS read-only
	STATUS mandatory
	DESCRIPTION
		"The current UPS automatic restart type"
	::= { upsIII3pAnalog 21 }

upsIII3pShutdownType OBJECT-TYPE
	SYNTAX INTEGER {
		shutdownOutputOnly(0),
		Entire(100)
	}
	ACCESS read-only
	STATUS mandatory
	DESCRIPTION
		"The current UPS shutdown type"
	::= { upsIII3pAnalog 22 }

upsIII3pBatCondition OBJECT-TYPE
	SYNTAX INTEGER {
		good(0),
		weak(100),
		replace(200)
	}
	ACCESS read-only
	STATUS mandatory
	DESCRIPTION
		"The current Battery Condition"
	::= { upsIII3pAnalog 23 }

upsIII3pBatStatus OBJECT-TYPE
	SYNTAX INTEGER {
		OK(0),
		Low(100),
		Depleted(200)
	}
	ACCESS read-only
	STATUS mandatory
	DESCRIPTION
		"The current Battery Status"
	::= { upsIII3pAnalog 24 }

upsIII3pBatChargeStatus OBJECT-TYPE
	SYNTAX INTEGER {
		floating(0),
		charging(100),
		resting(200),
		discharging(300)
	}
	ACCESS read-only
	STATUS mandatory
	DESCRIPTION
		"The current Battery Charge Status"
	::= { upsIII3pAnalog 25 }

--upsIII3pSecondOnBattery OBJECT-TYPE
--	SYNTAX INTEGER
--	ACCESS read-only
--	STATUS mandatory
--	DESCRIPTION
--		"The current UPS Senond On Battery in 1/100 Second"
--	::= { upsIII3pAnalog 26 }

upsIII3pEstimatedMinutesOnBat OBJECT-TYPE
	SYNTAX INTEGER
	ACCESS read-only
	STATUS mandatory
	DESCRIPTION
		"The current UPS estimated Minutes On Battery in 1/100 Minutes"
	::= { upsIII3pAnalog 26 }

upsIII3pEstimatedCharge OBJECT-TYPE
	SYNTAX INTEGER
	ACCESS read-only
	STATUS mandatory
	DESCRIPTION
		"The current UPS estimated Charge in 1/100 %"
	::= { upsIII3pAnalog 28 }

upsIII3pBatteryVol OBJECT-TYPE
	SYNTAX INTEGER
	ACCESS read-only
	STATUS mandatory
	DESCRIPTION
		"The current UPS Battery voltage in 1/100 V"
	::= { upsIII3pAnalog 29 }

upsIII3pBatteryCurrent OBJECT-TYPE
	SYNTAX INTEGER
	ACCESS read-only
	STATUS mandatory
	DESCRIPTION
		"The current UPS Battery Current in 1/100 A"
	::= { upsIII3pAnalog 30 }

upsIII3pBatteryTemperature OBJECT-TYPE
	SYNTAX INTEGER
	ACCESS read-only
	STATUS mandatory
	DESCRIPTION
		"The current UPS Battery Temperature in 1/100 C"
	::= { upsIII3pAnalog 31 }

upsIII3pInputLineBads OBJECT-TYPE
	SYNTAX INTEGER
	ACCESS read-only
	STATUS mandatory
	DESCRIPTION
		"The current UPS Input line bads in 1/100 line"
	::= { upsIII3pAnalog 32 }

upsIII3pInputLines OBJECT-TYPE
	SYNTAX INTEGER
	ACCESS read-only
	STATUS mandatory
	DESCRIPTION
		"The current UPS Input line in 1/100 line"
	::= { upsIII3pAnalog 33 }

upsIII3pInputLine1Fre OBJECT-TYPE
	SYNTAX INTEGER
	ACCESS read-only
	STATUS mandatory
	DESCRIPTION
		"The current UPS Input Line1 Fre in 1/100 Hz"
	::= { upsIII3pAnalog 34 }

upsIII3pInputLine1Vol OBJECT-TYPE
	SYNTAX INTEGER
	ACCESS read-only
	STATUS mandatory
	DESCRIPTION
		"The current UPS Input Line1 voltage in 1/100 V"
	::= { upsIII3pAnalog 35 }

upsIII3pInputLine1Cur OBJECT-TYPE
	SYNTAX INTEGER
	ACCESS read-only
	STATUS mandatory
	DESCRIPTION
		"The current UPS Input Line1 Current in 1/100 A"
	::= { upsIII3pAnalog 36 }

upsIII3pInputLine1Power OBJECT-TYPE
	SYNTAX INTEGER
	ACCESS read-only
	STATUS mandatory
	DESCRIPTION
		"The current UPS Input Line1 Power in 1/100 KW"
	::= { upsIII3pAnalog 37 }

upsIII3pInputLine2Fre OBJECT-TYPE
	SYNTAX INTEGER
	ACCESS read-only
	STATUS mandatory
	DESCRIPTION
		"The current UPS Input Line2 Fre in 1/100 Hz"
	::= { upsIII3pAnalog 38 }

upsIII3pInputLine2Vol OBJECT-TYPE
	SYNTAX INTEGER
	ACCESS read-only
	STATUS mandatory
	DESCRIPTION
		"The current UPS Input Line2 voltage in 1/100 V"
	::= { upsIII3pAnalog 39 }

upsIII3pInputLine2Cur OBJECT-TYPE
	SYNTAX INTEGER
	ACCESS read-only
	STATUS mandatory
	DESCRIPTION
		"The current UPS Input Line2 Current in 1/100 A"
	::= { upsIII3pAnalog 40 }

upsIII3pInputLine2Power OBJECT-TYPE
	SYNTAX INTEGER
	ACCESS read-only
	STATUS mandatory
	DESCRIPTION
		"The current UPS Input Line2 Power in 1/100 KW"
	::= { upsIII3pAnalog 41 }

upsIII3pInputLine3Fre OBJECT-TYPE
	SYNTAX INTEGER
	ACCESS read-only
	STATUS mandatory
	DESCRIPTION
		"The current UPS Input Line3 Fre in 1/100 Hz"
	::= { upsIII3pAnalog 42 }

upsIII3pInputLine3Vol OBJECT-TYPE
	SYNTAX INTEGER
	ACCESS read-only
	STATUS mandatory
	DESCRIPTION
		"The current UPS Input Line3 voltage in 1/100 V"
	::= { upsIII3pAnalog 43 }

upsIII3pInputLine3Cur OBJECT-TYPE
	SYNTAX INTEGER
	ACCESS read-only
	STATUS mandatory
	DESCRIPTION
		"The current UPS Input Line3 Current in 1/100 A"
	::= { upsIII3pAnalog 44 }

upsIII3pInputLine3Power OBJECT-TYPE
	SYNTAX INTEGER
	ACCESS read-only
	STATUS mandatory
	DESCRIPTION
		"The current UPS Input Line3 Power in 1/100 KW"
	::= { upsIII3pAnalog 45 }

upsIII3pOutputSource OBJECT-TYPE
	SYNTAX INTEGER {
		Normal(0),
		ByBattery(100),
		ByPass(200),
		Reduce(300),
		Boost(400),
		Other(500)
	}
	ACCESS read-only
	STATUS mandatory
	DESCRIPTION
		"The current UPS Output Source"
	::= { upsIII3pAnalog 46 }

upsIII3pOutputFre OBJECT-TYPE
	SYNTAX INTEGER
	ACCESS read-only
	STATUS mandatory
	DESCRIPTION
		"The current UPS Output Fre in 1/100 HZ"
	::= { upsIII3pAnalog 47 }

upsIII3pOutputLines OBJECT-TYPE
	SYNTAX INTEGER
	ACCESS read-only
	STATUS mandatory
	DESCRIPTION
		"The current UPS Output Lines in 1/100"
	::= { upsIII3pAnalog 48 }

upsIII3pOutputLine1Vol OBJECT-TYPE
	SYNTAX INTEGER
	ACCESS read-only
	STATUS mandatory
	DESCRIPTION
		"The current UPS Output Line1 voltage in 1/100 V"
	::= { upsIII3pAnalog 49 }

upsIII3pOutputLine1Cur OBJECT-TYPE
	SYNTAX INTEGER
	ACCESS read-only
	STATUS mandatory
	DESCRIPTION
		"The current UPS Output Line1 Current in 1/100 A"
	::= { upsIII3pAnalog 50 }

upsIII3pOutputLine1Power OBJECT-TYPE
	SYNTAX INTEGER
	ACCESS read-only
	STATUS mandatory
	DESCRIPTION
		"The current UPS Output Line1 Power in 1/100 KW"
	::= { upsIII3pAnalog 51 }

upsIII3pOutputLine1Load OBJECT-TYPE
	SYNTAX INTEGER
	ACCESS read-only
	STATUS mandatory
	DESCRIPTION
		"The current UPS Output Line1 Load in 1/100 %"
	::= { upsIII3pAnalog 52 }

upsIII3pOutputLine2Vol OBJECT-TYPE
	SYNTAX INTEGER
	ACCESS read-only
	STATUS mandatory
	DESCRIPTION
		"The current UPS Output Line2 voltage in 1/100 V"
	::= { upsIII3pAnalog 53 }

upsIII3pOutputLine2Cur OBJECT-TYPE
	SYNTAX INTEGER
	ACCESS read-only
	STATUS mandatory
	DESCRIPTION
		"The current UPS Output Line2 Current in 1/100 A"
	::= { upsIII3pAnalog 54 }

upsIII3pOutputLine2Power OBJECT-TYPE
	SYNTAX INTEGER
	ACCESS read-only
	STATUS mandatory
	DESCRIPTION
		"The current UPS Output Line2 Power in 1/100 KW"
	::= { upsIII3pAnalog 55 }

upsIII3pOutputLine2Load OBJECT-TYPE
	SYNTAX INTEGER
	ACCESS read-only
	STATUS mandatory
	DESCRIPTION
		"The current UPS Output Line2 Load in 1/100 %"
	::= { upsIII3pAnalog 56 }

upsIII3pOutputLine3Vol OBJECT-TYPE
	SYNTAX INTEGER
	ACCESS read-only
	STATUS mandatory
	DESCRIPTION
		"The current UPS Output Line3 voltage in 1/100 V"
	::= { upsIII3pAnalog 57 }

upsIII3pOutputLine3Cur OBJECT-TYPE
	SYNTAX INTEGER
	ACCESS read-only
	STATUS mandatory
	DESCRIPTION
		"The current UPS Output Line3 Current in 1/100 A"
	::= { upsIII3pAnalog 58 }

upsIII3pOutputLine3Power OBJECT-TYPE
	SYNTAX INTEGER
	ACCESS read-only
	STATUS mandatory
	DESCRIPTION
		"The current UPS Output Line3 Power in 1/100 KW"
	::= { upsIII3pAnalog 59 }

upsIII3pOutputLine3Load OBJECT-TYPE
	SYNTAX INTEGER
	ACCESS read-only
	STATUS mandatory
	DESCRIPTION
		"The current UPS Output Line3 Load in 1/100 %"
	::= { upsIII3pAnalog 60 }

upsIII3pBypassFre OBJECT-TYPE
	SYNTAX INTEGER
	ACCESS read-only
	STATUS mandatory
	DESCRIPTION
		"The current UPS Bypass Fre in 1/100 HZ"
	::= { upsIII3pAnalog 61 }

upsIII3pBypassLines OBJECT-TYPE
	SYNTAX INTEGER
	ACCESS read-only
	STATUS mandatory
	DESCRIPTION
		"The current UPS Bypass Lines in 1/100"
	::= { upsIII3pAnalog 62 }

upsIII3pBypassLine1Vol OBJECT-TYPE
	SYNTAX INTEGER
	ACCESS read-only
	STATUS mandatory
	DESCRIPTION
		"The current UPS Bypass Line1 voltage in 1/100 V"
	::= { upsIII3pAnalog 63 }

upsIII3pBypassLine1Cur OBJECT-TYPE
	SYNTAX INTEGER
	ACCESS read-only
	STATUS mandatory
	DESCRIPTION
		"The current UPS Bypass Line1 Current in 1/100 A"
	::= { upsIII3pAnalog 64 }

upsIII3pBypassLine1Power OBJECT-TYPE
	SYNTAX INTEGER
	ACCESS read-only
	STATUS mandatory
	DESCRIPTION
		"The current UPS Bypass Line1 Power in 1/100 W"
	::= { upsIII3pAnalog 65 }

upsIII3pBypassLine2Vol OBJECT-TYPE
	SYNTAX INTEGER
	ACCESS read-only
	STATUS mandatory
	DESCRIPTION
		"The current UPS Bypass Line2 voltage in 1/100 V"
	::= { upsIII3pAnalog 66 }

upsIII3pBypassLine2Cur OBJECT-TYPE
	SYNTAX INTEGER
	ACCESS read-only
	STATUS mandatory
	DESCRIPTION
		"The current UPS Bypass Line2 Current in 1/100 A"
	::= { upsIII3pAnalog 67 }

upsIII3pBypassLine2Power OBJECT-TYPE
	SYNTAX INTEGER
	ACCESS read-only
	STATUS mandatory
	DESCRIPTION
		"The current UPS Bypass Line2 Power in 1/100 W"
	::= { upsIII3pAnalog 68 }

upsIII3pBypassLine3Vol OBJECT-TYPE
	SYNTAX INTEGER
	ACCESS read-only
	STATUS mandatory
	DESCRIPTION
		"The current UPS Bypass Line3 voltage in 1/100 V"
	::= { upsIII3pAnalog 69 }

upsIII3pBypassLine3Cur OBJECT-TYPE
	SYNTAX INTEGER
	ACCESS read-only
	STATUS mandatory
	DESCRIPTION
		"The current UPS Bypass Line3 Current in 1/100 A"
	::= { upsIII3pAnalog 70 }

upsIII3pBypassLine3Power OBJECT-TYPE
	SYNTAX INTEGER
	ACCESS read-only
	STATUS mandatory
	DESCRIPTION
		"The current UPS Bypass Line3 Power in 1/100 W"
	::= { upsIII3pAnalog 71 }

upsIII3pTestResult OBJECT-TYPE
	SYNTAX INTEGER {
		NoTest(0),
		TestPass(100),
		TestInProgress(200),
		GeneralTestFail(300),
		BatteryTestFail(400),
		DeepBatteryTestFail(500)
	}
	ACCESS read-only
	STATUS mandatory
	DESCRIPTION
		"The current UPS Test result"
	::= { upsIII3pAnalog 72 }

upsIII3pOutputTotalPower OBJECT-TYPE
	SYNTAX INTEGER
	ACCESS read-only
	STATUS mandatory
	DESCRIPTION
		"The current UPS output Total Power in 1/100 W"
	::= { upsIII3pAnalog 73 }

upsIII3pBatteryCap OBJECT-TYPE
	SYNTAX INTEGER
	ACCESS read-only
	STATUS mandatory
	DESCRIPTION
		"The current UPS Temperature in 1/100 C"
	::= { upsIII3pAnalog 74 }

upsIII3pTemperature OBJECT-TYPE
	SYNTAX INTEGER
	ACCESS read-only
	STATUS mandatory
	DESCRIPTION
		"The current UPS Fault ID in 1/100"
	::= { upsIII3pAnalog 75 }

-- the upsIII3pSwitch group
upsIII3pTemperatureTooHigh OBJECT-TYPE
	SYNTAX INTEGER  {
		normal(0),
		occur(1)
	}
	ACCESS read-only
	STATUS mandatory
	DESCRIPTION
		"Temperature too High!"
	::= { upsIII3pSwitch 17 }

upsIII3pInputFault OBJECT-TYPE
	SYNTAX INTEGER  {
		normal(0),
		occur(1)
	}
	ACCESS read-only
	STATUS mandatory
	DESCRIPTION
		"Input Fault!"
	::= { upsIII3pSwitch 18 }

upsIII3pOutputFault OBJECT-TYPE
	SYNTAX INTEGER  {
		normal(0),
		occur(1)
	}
	ACCESS read-only
	STATUS mandatory
	DESCRIPTION
		"Output Fault!"
	::= { upsIII3pSwitch 19 }

upsIII3pOverLoad OBJECT-TYPE
	SYNTAX INTEGER  {
		normal(0),
		occur(1)
	}
	ACCESS read-only
	STATUS mandatory
	DESCRIPTION
		"Over Load!"
	::= { upsIII3pSwitch 20 }

upsIII3pBypassFault OBJECT-TYPE
	SYNTAX INTEGER  {
		normal(0),
		occur(1)
	}
	ACCESS read-only
	STATUS mandatory
	DESCRIPTION
		"Bapass Fault!"
	::= { upsIII3pSwitch 21 }

upsIII3pOutputShutdown OBJECT-TYPE
	SYNTAX INTEGER  {
		normal(0),
		occur(1)
	}
	ACCESS read-only
	STATUS mandatory
	DESCRIPTION
		"Output Shutdown"
	::= { upsIII3pSwitch 22 }

upsIII3pShutdown OBJECT-TYPE
	SYNTAX INTEGER  {
		normal(0),
		occur(1)
	}
	ACCESS read-only
	STATUS mandatory
	DESCRIPTION
		"UPS Shutdown!"
	::= { upsIII3pSwitch 23 }

upsIII3pChargeFault OBJECT-TYPE
	SYNTAX INTEGER  {
		normal(0),
		occur(1)
	}
	ACCESS read-only
	STATUS mandatory
	DESCRIPTION
		"Battery charge Fault!"
	::= { upsIII3pSwitch 24 }

upsIII3pSystemShutdown OBJECT-TYPE
	SYNTAX INTEGER  {
		normal(0),
		occur(1)
	}
	ACCESS read-only
	STATUS mandatory
	DESCRIPTION
		"System Shutdown!"
	::= { upsIII3pSwitch 25 }

upsIII3pFanFault OBJECT-TYPE
	SYNTAX INTEGER  {
		normal(0),
		occur(1)
	}
	ACCESS read-only
	STATUS mandatory
	DESCRIPTION
		"Fan Fault!"
	::= { upsIII3pSwitch 26 }

upsIII3pFuseFault OBJECT-TYPE
	SYNTAX INTEGER  {
		normal(0),
		occur(1)
	}
	ACCESS read-only
	STATUS mandatory
	DESCRIPTION
		"Fuse Fault!"
	::= { upsIII3pSwitch 27 }

upsIII3pGeneralFault OBJECT-TYPE
	SYNTAX INTEGER  {
		normal(0),
		occur(1)
	}
	ACCESS read-only
	STATUS mandatory
	DESCRIPTION
		"Gereral Fault!"
	::= { upsIII3pSwitch 28 }

upsIII3pAutoRestart OBJECT-TYPE
	SYNTAX INTEGER  {
		normal(0),
		occur(1)
	}
	ACCESS read-only
	STATUS mandatory
	DESCRIPTION
		"automatic Restart!"
	::= { upsIII3pSwitch 29 }

upsIII3pShutdownDelayStatus OBJECT-TYPE
	SYNTAX INTEGER  {
		normal(0),
		occur(1)
	}
	ACCESS read-only
	STATUS mandatory
	DESCRIPTION
		"Shutdown delay!"
	::= { upsIII3pSwitch 30 }

upsIII3pShutdownAtonce OBJECT-TYPE
	SYNTAX INTEGER  {
		normal(0),
		occur(1)
	}
	ACCESS read-only
	STATUS mandatory
	DESCRIPTION
		"Shutdown at once!"
	::= { upsIII3pSwitch 31 }

usp3Communication OBJECT-TYPE
	SYNTAX INTEGER  {
		normal(0),
		occur(1)
	}
	ACCESS read-only
	STATUS mandatory
	DESCRIPTION
		"Communication status!"
	::= { upsIII3pSwitch 32 }

upsIII3pBatteryFault OBJECT-TYPE
	SYNTAX INTEGER  {
		normal(0),
		occur(1)
	}
	ACCESS read-only
	STATUS mandatory
	DESCRIPTION
		"battery Fault!"
	::= { upsIII3pSwitch 33 }

upsIII3pBatteryVolLow OBJECT-TYPE
	SYNTAX INTEGER  {
		normal(0),
		occur(1)
	}
	ACCESS read-only
	STATUS mandatory
	DESCRIPTION
		"battery voltage too low!"
	::= { upsIII3pSwitch 34 }

upsIII3pBypass OBJECT-TYPE
	SYNTAX INTEGER  {
		normal(0),
		occur(1)
	}
	ACCESS read-only
	STATUS mandatory
	DESCRIPTION
		"Bypass!"
	::= { upsIII3pSwitch 35 }

upsIII3pOtherFault OBJECT-TYPE
	SYNTAX INTEGER  {
		normal(0),
		occur(1)
	}
	ACCESS read-only
	STATUS mandatory
	DESCRIPTION
		"Other Fault!"
	::= { upsIII3pSwitch 36 }

upsIII3pTestInProgress OBJECT-TYPE
	SYNTAX INTEGER  {
		normal(0),
		occur(1)
	}
	ACCESS read-only
	STATUS mandatory
	DESCRIPTION
		"Now Testing!"
	::= { upsIII3pSwitch 37 }

upsIII3pRectifierFailure OBJECT-TYPE
	SYNTAX INTEGER  {
		normal(0),
		occur(1)
	}
	ACCESS read-only
	STATUS mandatory
	DESCRIPTION
		"Rectifier Failure!"
	::= { upsIII3pSwitch 100 }

upsIII3pInverterFailure OBJECT-TYPE
	SYNTAX INTEGER  {
		normal(0),
		occur(1)
	}
	ACCESS read-only
	STATUS mandatory
	DESCRIPTION
		"Inverter Failure!"
	::= { upsIII3pSwitch 101 }
	
-- the upsIII3pControl group
upsIII3pTest OBJECT-TYPE
	SYNTAX INTEGER 
	ACCESS read-write
	STATUS mandatory
	DESCRIPTION
		"0:cancle test; -1:Test till battery voltage low; other:test Some Time"
	::= { upsIII3pControl 1 }

upsIII3pShutdownDelay OBJECT-TYPE
	SYNTAX INTEGER 
	ACCESS read-write
	STATUS mandatory
	DESCRIPTION
		"0:cancle shutdown; other:Shutdown ups after delay UNIT:second"
	::= { upsIII3pControl 2 }

upsIII3pRestartDelay OBJECT-TYPE
	SYNTAX INTEGER 
	ACCESS read-write
	STATUS mandatory
	DESCRIPTION
		"Restart ups after delay UNIT:second"
	::= { upsIII3pControl 3 }

-- the upsIII3pStrInfo group
upsIII3pManufacturer  OBJECT-TYPE
	SYNTAX DisplayString
	ACCESS read-only
	STATUS mandatory
	DESCRIPTION
		"The UPS Manufacturer name (e.g. 'richcomm')."
	::= { upsIII3pStrInfo 1 }

upsIII3pModel  OBJECT-TYPE
	SYNTAX DisplayString
	ACCESS read-only
	STATUS mandatory
	DESCRIPTION
		"The UPS Model name (e.g. 'RC-600VA')."
	::= { upsIII3pStrInfo 2 }

upsIII3pVersion OBJECT-TYPE
	SYNTAX DisplayString
	ACCESS read-only
	STATUS mandatory
	DESCRIPTION
		"The firmware revision of the UPS system"
	::= { upsIII3pStrInfo 3 }

upsIII3pRateInputVol OBJECT-TYPE
	SYNTAX INTEGER
	UNITS     "0.01 V"
	ACCESS read-only
	STATUS mandatory
	DESCRIPTION
		"The Rate Input voltage of the UPS system"
	::= { upsIII3pStrInfo 4 }

upsIII3pRateCurrent OBJECT-TYPE
	SYNTAX INTEGER
	UNITS     "0.01 A"
	ACCESS read-only
	STATUS mandatory
	DESCRIPTION
		"The Rate Current of the UPS system"
	::= { upsIII3pStrInfo 5 }

upsIII3pRateBatVol OBJECT-TYPE
	SYNTAX INTEGER
	UNITS     "0.01 V"
	ACCESS read-only
	STATUS mandatory
	DESCRIPTION
		"The Rate battery voltage of the UPS system"
	::= { upsIII3pStrInfo 6 }

upsIII3pRateFre OBJECT-TYPE
	SYNTAX INTEGER
	UNITS     "0.01 Hz"
	ACCESS read-only
	STATUS mandatory
	DESCRIPTION
		"The Rate Frequency of the UPS system"
	::= { upsIII3pStrInfo 7 }
-- ****************************upsIV3p************************************
upsIV3pAnalog                       OBJECT IDENTIFIER ::=  { upsIV3p 1 }
upsIV3pSwitch                       OBJECT IDENTIFIER ::=  { upsIV3p 2 }
upsIV3pControl                      OBJECT IDENTIFIER ::=  { upsIV3p 3 }
upsIV3pStrInfo                      OBJECT IDENTIFIER ::=  { upsIV3p 4 }
-- the upsIV3pAnalog group

upsIV3pAutoRestartType OBJECT-TYPE
	SYNTAX INTEGER {
		automatic(0),
		manual(100)
	}
	ACCESS read-only
	STATUS mandatory
	DESCRIPTION
		"The current UPS automatic restart type"
	::= { upsIV3pAnalog 21 }

upsIV3pShutdownType OBJECT-TYPE
	SYNTAX INTEGER {
		shutdownOutputOnly(0),
		Entire(100)
	}
	ACCESS read-only
	STATUS mandatory
	DESCRIPTION
		"The current UPS shutdown type"
	::= { upsIV3pAnalog 22 }

upsIV3pBatCondition OBJECT-TYPE
	SYNTAX INTEGER {
		good(0),
		weak(100),
		replace(200)
	}
	ACCESS read-only
	STATUS mandatory
	DESCRIPTION
		"The current Battery Condition"
	::= { upsIV3pAnalog 23 }

upsIV3pBatStatus OBJECT-TYPE
	SYNTAX INTEGER {
		OK(0),
		Low(100),
		Depleted(200)
	}
	ACCESS read-only
	STATUS mandatory
	DESCRIPTION
		"The current Battery Status"
	::= { upsIV3pAnalog 24 }

upsIV3pBatChargeStatus OBJECT-TYPE
	SYNTAX INTEGER {
		floating(0),
		charging(100),
		resting(200),
		discharging(300)
	}
	ACCESS read-only
	STATUS mandatory
	DESCRIPTION
		"The current Battery Charge Status"
	::= { upsIV3pAnalog 25 }

--upsIV3pSecondOnBattery OBJECT-TYPE
--	SYNTAX INTEGER
--	ACCESS read-only
--	STATUS mandatory
--	DESCRIPTION
--		"The current UPS Senond On Battery in 1/100 Second"
--	::= { upsIV3pAnalog 26 }

upsIV3pEstimatedMinutesOnBat OBJECT-TYPE
	SYNTAX INTEGER
	ACCESS read-only
	STATUS mandatory
	DESCRIPTION
		"The current UPS estimated Minutes On Battery in 1/100 Minutes"
	::= { upsIV3pAnalog 26 }

upsIV3pEstimatedCharge OBJECT-TYPE
	SYNTAX INTEGER
	ACCESS read-only
	STATUS mandatory
	DESCRIPTION
		"The current UPS estimated Charge in 1/100 %"
	::= { upsIV3pAnalog 28 }

upsIV3pBatteryVol OBJECT-TYPE
	SYNTAX INTEGER
	ACCESS read-only
	STATUS mandatory
	DESCRIPTION
		"The current UPS Battery voltage in 1/100 V"
	::= { upsIV3pAnalog 29 }

upsIV3pBatteryCurrent OBJECT-TYPE
	SYNTAX INTEGER
	ACCESS read-only
	STATUS mandatory
	DESCRIPTION
		"The current UPS Battery Current in 1/100 A"
	::= { upsIV3pAnalog 30 }

upsIV3pBatteryTemperature OBJECT-TYPE
	SYNTAX INTEGER
	ACCESS read-only
	STATUS mandatory
	DESCRIPTION
		"The current UPS Battery Temperature in 1/100 C"
	::= { upsIV3pAnalog 31 }

upsIV3pInputLineBads OBJECT-TYPE
	SYNTAX INTEGER
	ACCESS read-only
	STATUS mandatory
	DESCRIPTION
		"The current UPS Input line bads in 1/100 line"
	::= { upsIV3pAnalog 32 }

upsIV3pInputLines OBJECT-TYPE
	SYNTAX INTEGER
	ACCESS read-only
	STATUS mandatory
	DESCRIPTION
		"The current UPS Input line in 1/100 line"
	::= { upsIV3pAnalog 33 }

upsIV3pInputLine1Fre OBJECT-TYPE
	SYNTAX INTEGER
	ACCESS read-only
	STATUS mandatory
	DESCRIPTION
		"The current UPS Input Line1 Fre in 1/100 Hz"
	::= { upsIV3pAnalog 34 }

upsIV3pInputLine1Vol OBJECT-TYPE
	SYNTAX INTEGER
	ACCESS read-only
	STATUS mandatory
	DESCRIPTION
		"The current UPS Input Line1 voltage in 1/100 V"
	::= { upsIV3pAnalog 35 }

upsIV3pInputLine1Cur OBJECT-TYPE
	SYNTAX INTEGER
	ACCESS read-only
	STATUS mandatory
	DESCRIPTION
		"The current UPS Input Line1 Current in 1/100 A"
	::= { upsIV3pAnalog 36 }

upsIV3pInputLine1Power OBJECT-TYPE
	SYNTAX INTEGER
	ACCESS read-only
	STATUS mandatory
	DESCRIPTION
		"The current UPS Input Line1 Power in 1/100 KW"
	::= { upsIV3pAnalog 37 }

upsIV3pInputLine2Fre OBJECT-TYPE
	SYNTAX INTEGER
	ACCESS read-only
	STATUS mandatory
	DESCRIPTION
		"The current UPS Input Line2 Fre in 1/100 Hz"
	::= { upsIV3pAnalog 38 }

upsIV3pInputLine2Vol OBJECT-TYPE
	SYNTAX INTEGER
	ACCESS read-only
	STATUS mandatory
	DESCRIPTION
		"The current UPS Input Line2 voltage in 1/100 V"
	::= { upsIV3pAnalog 39 }

upsIV3pInputLine2Cur OBJECT-TYPE
	SYNTAX INTEGER
	ACCESS read-only
	STATUS mandatory
	DESCRIPTION
		"The current UPS Input Line2 Current in 1/100 A"
	::= { upsIV3pAnalog 40 }

upsIV3pInputLine2Power OBJECT-TYPE
	SYNTAX INTEGER
	ACCESS read-only
	STATUS mandatory
	DESCRIPTION
		"The current UPS Input Line2 Power in 1/100 KW"
	::= { upsIV3pAnalog 41 }

upsIV3pInputLine3Fre OBJECT-TYPE
	SYNTAX INTEGER
	ACCESS read-only
	STATUS mandatory
	DESCRIPTION
		"The current UPS Input Line3 Fre in 1/100 Hz"
	::= { upsIV3pAnalog 42 }

upsIV3pInputLine3Vol OBJECT-TYPE
	SYNTAX INTEGER
	ACCESS read-only
	STATUS mandatory
	DESCRIPTION
		"The current UPS Input Line3 voltage in 1/100 V"
	::= { upsIV3pAnalog 43 }

upsIV3pInputLine3Cur OBJECT-TYPE
	SYNTAX INTEGER
	ACCESS read-only
	STATUS mandatory
	DESCRIPTION
		"The current UPS Input Line3 Current in 1/100 A"
	::= { upsIV3pAnalog 44 }

upsIV3pInputLine3Power OBJECT-TYPE
	SYNTAX INTEGER
	ACCESS read-only
	STATUS mandatory
	DESCRIPTION
		"The current UPS Input Line3 Power in 1/100 KW"
	::= { upsIV3pAnalog 45 }

upsIV3pOutputSource OBJECT-TYPE
	SYNTAX INTEGER {
		Normal(0),
		ByBattery(100),
		ByPass(200),
		Reduce(300),
		Boost(400),
		Other(500)
	}
	ACCESS read-only
	STATUS mandatory
	DESCRIPTION
		"The current UPS Output Source"
	::= { upsIV3pAnalog 46 }

upsIV3pOutputFre OBJECT-TYPE
	SYNTAX INTEGER
	ACCESS read-only
	STATUS mandatory
	DESCRIPTION
		"The current UPS Output Fre in 1/100 HZ"
	::= { upsIV3pAnalog 47 }

upsIV3pOutputLines OBJECT-TYPE
	SYNTAX INTEGER
	ACCESS read-only
	STATUS mandatory
	DESCRIPTION
		"The current UPS Output Lines in 1/100"
	::= { upsIV3pAnalog 48 }

upsIV3pOutputLine1Vol OBJECT-TYPE
	SYNTAX INTEGER
	ACCESS read-only
	STATUS mandatory
	DESCRIPTION
		"The current UPS Output Line1 voltage in 1/100 V"
	::= { upsIV3pAnalog 49 }

upsIV3pOutputLine1Cur OBJECT-TYPE
	SYNTAX INTEGER
	ACCESS read-only
	STATUS mandatory
	DESCRIPTION
		"The current UPS Output Line1 Current in 1/100 A"
	::= { upsIV3pAnalog 50 }

upsIV3pOutputLine1Power OBJECT-TYPE
	SYNTAX INTEGER
	ACCESS read-only
	STATUS mandatory
	DESCRIPTION
		"The current UPS Output Line1 Power in 1/100 KW"
	::= { upsIV3pAnalog 51 }

upsIV3pOutputLine1Load OBJECT-TYPE
	SYNTAX INTEGER
	ACCESS read-only
	STATUS mandatory
	DESCRIPTION
		"The current UPS Output Line1 Load in 1/100 %"
	::= { upsIV3pAnalog 52 }

upsIV3pOutputLine2Vol OBJECT-TYPE
	SYNTAX INTEGER
	ACCESS read-only
	STATUS mandatory
	DESCRIPTION
		"The current UPS Output Line2 voltage in 1/100 V"
	::= { upsIV3pAnalog 53 }

upsIV3pOutputLine2Cur OBJECT-TYPE
	SYNTAX INTEGER
	ACCESS read-only
	STATUS mandatory
	DESCRIPTION
		"The current UPS Output Line2 Current in 1/100 A"
	::= { upsIV3pAnalog 54 }

upsIV3pOutputLine2Power OBJECT-TYPE
	SYNTAX INTEGER
	ACCESS read-only
	STATUS mandatory
	DESCRIPTION
		"The current UPS Output Line2 Power in 1/100 KW"
	::= { upsIV3pAnalog 55 }

upsIV3pOutputLine2Load OBJECT-TYPE
	SYNTAX INTEGER
	ACCESS read-only
	STATUS mandatory
	DESCRIPTION
		"The current UPS Output Line2 Load in 1/100 %"
	::= { upsIV3pAnalog 56 }

upsIV3pOutputLine3Vol OBJECT-TYPE
	SYNTAX INTEGER
	ACCESS read-only
	STATUS mandatory
	DESCRIPTION
		"The current UPS Output Line3 voltage in 1/100 V"
	::= { upsIV3pAnalog 57 }

upsIV3pOutputLine3Cur OBJECT-TYPE
	SYNTAX INTEGER
	ACCESS read-only
	STATUS mandatory
	DESCRIPTION
		"The current UPS Output Line3 Current in 1/100 A"
	::= { upsIV3pAnalog 58 }

upsIV3pOutputLine3Power OBJECT-TYPE
	SYNTAX INTEGER
	ACCESS read-only
	STATUS mandatory
	DESCRIPTION
		"The current UPS Output Line3 Power in 1/100 KW"
	::= { upsIV3pAnalog 59 }

upsIV3pOutputLine3Load OBJECT-TYPE
	SYNTAX INTEGER
	ACCESS read-only
	STATUS mandatory
	DESCRIPTION
		"The current UPS Output Line3 Load in 1/100 %"
	::= { upsIV3pAnalog 60 }

upsIV3pBypassFre OBJECT-TYPE
	SYNTAX INTEGER
	ACCESS read-only
	STATUS mandatory
	DESCRIPTION
		"The current UPS Bypass Fre in 1/100 HZ"
	::= { upsIV3pAnalog 61 }

upsIV3pBypassLines OBJECT-TYPE
	SYNTAX INTEGER
	ACCESS read-only
	STATUS mandatory
	DESCRIPTION
		"The current UPS Bypass Lines in 1/100"
	::= { upsIV3pAnalog 62 }

upsIV3pBypassLine1Vol OBJECT-TYPE
	SYNTAX INTEGER
	ACCESS read-only
	STATUS mandatory
	DESCRIPTION
		"The current UPS Bypass Line1 voltage in 1/100 V"
	::= { upsIV3pAnalog 63 }

upsIV3pBypassLine1Cur OBJECT-TYPE
	SYNTAX INTEGER
	ACCESS read-only
	STATUS mandatory
	DESCRIPTION
		"The current UPS Bypass Line1 Current in 1/100 A"
	::= { upsIV3pAnalog 64 }

upsIV3pBypassLine1Power OBJECT-TYPE
	SYNTAX INTEGER
	ACCESS read-only
	STATUS mandatory
	DESCRIPTION
		"The current UPS Bypass Line1 Power in 1/100 W"
	::= { upsIV3pAnalog 65 }

upsIV3pBypassLine2Vol OBJECT-TYPE
	SYNTAX INTEGER
	ACCESS read-only
	STATUS mandatory
	DESCRIPTION
		"The current UPS Bypass Line2 voltage in 1/100 V"
	::= { upsIV3pAnalog 66 }

upsIV3pBypassLine2Cur OBJECT-TYPE
	SYNTAX INTEGER
	ACCESS read-only
	STATUS mandatory
	DESCRIPTION
		"The current UPS Bypass Line2 Current in 1/100 A"
	::= { upsIV3pAnalog 67 }

upsIV3pBypassLine2Power OBJECT-TYPE
	SYNTAX INTEGER
	ACCESS read-only
	STATUS mandatory
	DESCRIPTION
		"The current UPS Bypass Line2 Power in 1/100 W"
	::= { upsIV3pAnalog 68 }

upsIV3pBypassLine3Vol OBJECT-TYPE
	SYNTAX INTEGER
	ACCESS read-only
	STATUS mandatory
	DESCRIPTION
		"The current UPS Bypass Line3 voltage in 1/100 V"
	::= { upsIV3pAnalog 69 }

upsIV3pBypassLine3Cur OBJECT-TYPE
	SYNTAX INTEGER
	ACCESS read-only
	STATUS mandatory
	DESCRIPTION
		"The current UPS Bypass Line3 Current in 1/100 A"
	::= { upsIV3pAnalog 70 }

upsIV3pBypassLine3Power OBJECT-TYPE
	SYNTAX INTEGER
	ACCESS read-only
	STATUS mandatory
	DESCRIPTION
		"The current UPS Bypass Line3 Power in 1/100 W"
	::= { upsIV3pAnalog 71 }

upsIV3pTestResult OBJECT-TYPE
	SYNTAX INTEGER {
		NoTest(0),
		TestPass(100),
		TestInProgress(200),
		GeneralTestFail(300),
		BatteryTestFail(400),
		DeepBatteryTestFail(500)
	}
	ACCESS read-only
	STATUS mandatory
	DESCRIPTION
		"The current UPS Test result"
	::= { upsIV3pAnalog 72 }

upsIV3pOutputTotalPower OBJECT-TYPE
	SYNTAX INTEGER
	ACCESS read-only
	STATUS mandatory
	DESCRIPTION
		"The current UPS output Total Power in 1/100 W"
	::= { upsIV3pAnalog 73 }

upsIV3pBatteryCap OBJECT-TYPE
	SYNTAX INTEGER
	ACCESS read-only
	STATUS mandatory
	DESCRIPTION
		"The current UPS Temperature in 1/100 C"
	::= { upsIV3pAnalog 74 }

upsIV3pTemperature OBJECT-TYPE
	SYNTAX INTEGER
	ACCESS read-only
	STATUS mandatory
	DESCRIPTION
		"The current UPS Fault ID in 1/100"
	::= { upsIV3pAnalog 75 }

-- the upsIV3pSwitch group
upsIV3pTemperatureTooHigh OBJECT-TYPE
	SYNTAX INTEGER  {
		normal(0),
		occur(1)
	}
	ACCESS read-only
	STATUS mandatory
	DESCRIPTION
		"Temperature too High!"
	::= { upsIV3pSwitch 17 }

upsIV3pInputFault OBJECT-TYPE
	SYNTAX INTEGER  {
		normal(0),
		occur(1)
	}
	ACCESS read-only
	STATUS mandatory
	DESCRIPTION
		"Input Fault!"
	::= { upsIV3pSwitch 18 }

upsIV3pOutputFault OBJECT-TYPE
	SYNTAX INTEGER  {
		normal(0),
		occur(1)
	}
	ACCESS read-only
	STATUS mandatory
	DESCRIPTION
		"Output Fault!"
	::= { upsIV3pSwitch 19 }

upsIV3pOverLoad OBJECT-TYPE
	SYNTAX INTEGER  {
		normal(0),
		occur(1)
	}
	ACCESS read-only
	STATUS mandatory
	DESCRIPTION
		"Over Load!"
	::= { upsIV3pSwitch 20 }

upsIV3pBypassFault OBJECT-TYPE
	SYNTAX INTEGER  {
		normal(0),
		occur(1)
	}
	ACCESS read-only
	STATUS mandatory
	DESCRIPTION
		"Bapass Fault!"
	::= { upsIV3pSwitch 21 }

upsIV3pOutputShutdown OBJECT-TYPE
	SYNTAX INTEGER  {
		normal(0),
		occur(1)
	}
	ACCESS read-only
	STATUS mandatory
	DESCRIPTION
		"Output Shutdown"
	::= { upsIV3pSwitch 22 }

upsIV3pShutdown OBJECT-TYPE
	SYNTAX INTEGER  {
		normal(0),
		occur(1)
	}
	ACCESS read-only
	STATUS mandatory
	DESCRIPTION
		"UPS Shutdown!"
	::= { upsIV3pSwitch 23 }

upsIV3pChargeFault OBJECT-TYPE
	SYNTAX INTEGER  {
		normal(0),
		occur(1)
	}
	ACCESS read-only
	STATUS mandatory
	DESCRIPTION
		"Battery charge Fault!"
	::= { upsIV3pSwitch 24 }

upsIV3pSystemShutdown OBJECT-TYPE
	SYNTAX INTEGER  {
		normal(0),
		occur(1)
	}
	ACCESS read-only
	STATUS mandatory
	DESCRIPTION
		"System Shutdown!"
	::= { upsIV3pSwitch 25 }

upsIV3pFanFault OBJECT-TYPE
	SYNTAX INTEGER  {
		normal(0),
		occur(1)
	}
	ACCESS read-only
	STATUS mandatory
	DESCRIPTION
		"Fan Fault!"
	::= { upsIV3pSwitch 26 }

upsIV3pFuseFault OBJECT-TYPE
	SYNTAX INTEGER  {
		normal(0),
		occur(1)
	}
	ACCESS read-only
	STATUS mandatory
	DESCRIPTION
		"Fuse Fault!"
	::= { upsIV3pSwitch 27 }

upsIV3pGeneralFault OBJECT-TYPE
	SYNTAX INTEGER  {
		normal(0),
		occur(1)
	}
	ACCESS read-only
	STATUS mandatory
	DESCRIPTION
		"Gereral Fault!"
	::= { upsIV3pSwitch 28 }

upsIV3pAutoRestart OBJECT-TYPE
	SYNTAX INTEGER  {
		normal(0),
		occur(1)
	}
	ACCESS read-only
	STATUS mandatory
	DESCRIPTION
		"automatic Restart!"
	::= { upsIV3pSwitch 29 }

upsIV3pShutdownDelayStatus OBJECT-TYPE
	SYNTAX INTEGER  {
		normal(0),
		occur(1)
	}
	ACCESS read-only
	STATUS mandatory
	DESCRIPTION
		"Shutdown delay!"
	::= { upsIV3pSwitch 30 }

upsIV3pShutdownAtonce OBJECT-TYPE
	SYNTAX INTEGER  {
		normal(0),
		occur(1)
	}
	ACCESS read-only
	STATUS mandatory
	DESCRIPTION
		"Shutdown at once!"
	::= { upsIV3pSwitch 31 }

usp4Communication OBJECT-TYPE
	SYNTAX INTEGER  {
		normal(0),
		occur(1)
	}
	ACCESS read-only
	STATUS mandatory
	DESCRIPTION
		"Communication status!"
	::= { upsIV3pSwitch 32 }

upsIV3pBatteryFault OBJECT-TYPE
	SYNTAX INTEGER  {
		normal(0),
		occur(1)
	}
	ACCESS read-only
	STATUS mandatory
	DESCRIPTION
		"battery Fault!"
	::= { upsIV3pSwitch 33 }

upsIV3pBatteryVolLow OBJECT-TYPE
	SYNTAX INTEGER  {
		normal(0),
		occur(1)
	}
	ACCESS read-only
	STATUS mandatory
	DESCRIPTION
		"battery voltage too low!"
	::= { upsIV3pSwitch 34 }

upsIV3pBypass OBJECT-TYPE
	SYNTAX INTEGER  {
		normal(0),
		occur(1)
	}
	ACCESS read-only
	STATUS mandatory
	DESCRIPTION
		"Bypass!"
	::= { upsIV3pSwitch 35 }

upsIV3pOtherFault OBJECT-TYPE
	SYNTAX INTEGER  {
		normal(0),
		occur(1)
	}
	ACCESS read-only
	STATUS mandatory
	DESCRIPTION
		"Other Fault!"
	::= { upsIV3pSwitch 36 }

upsIV3pTestInProgress OBJECT-TYPE
	SYNTAX INTEGER  {
		normal(0),
		occur(1)
	}
	ACCESS read-only
	STATUS mandatory
	DESCRIPTION
		"Now Testing!"
	::= { upsIV3pSwitch 37 }

upsIV3pRectifierFailure OBJECT-TYPE
	SYNTAX INTEGER  {
		normal(0),
		occur(1)
	}
	ACCESS read-only
	STATUS mandatory
	DESCRIPTION
		"Rectifier Failure!"
	::= { upsIV3pSwitch 100 }

upsIV3pInverterFailure OBJECT-TYPE
	SYNTAX INTEGER  {
		normal(0),
		occur(1)
	}
	ACCESS read-only
	STATUS mandatory
	DESCRIPTION
		"Inverter Failure!"
	::= { upsIV3pSwitch 101 }
	
-- the upsIV3pControl group
upsIV3pTest OBJECT-TYPE
	SYNTAX INTEGER 
	ACCESS read-write
	STATUS mandatory
	DESCRIPTION
		"0:cancle test; -1:Test till battery voltage low; other:test Some Time"
	::= { upsIV3pControl 1 }

upsIV3pShutdownDelay OBJECT-TYPE
	SYNTAX INTEGER 
	ACCESS read-write
	STATUS mandatory
	DESCRIPTION
		"0:cancle shutdown; other:Shutdown ups after delay UNIT:second"
	::= { upsIV3pControl 2 }

upsIV3pRestartDelay OBJECT-TYPE
	SYNTAX INTEGER 
	ACCESS read-write
	STATUS mandatory
	DESCRIPTION
		"Restart ups after delay UNIT:second"
	::= { upsIV3pControl 3 }

-- the upsIV3pStrInfo group
upsIV3pManufacturer  OBJECT-TYPE
	SYNTAX DisplayString
	ACCESS read-only
	STATUS mandatory
	DESCRIPTION
		"The UPS Manufacturer name (e.g. 'richcomm')."
	::= { upsIV3pStrInfo 1 }

upsIV3pModel  OBJECT-TYPE
	SYNTAX DisplayString
	ACCESS read-only
	STATUS mandatory
	DESCRIPTION
		"The UPS Model name (e.g. 'RC-600VA')."
	::= { upsIV3pStrInfo 2 }

upsIV3pVersion OBJECT-TYPE
	SYNTAX DisplayString
	ACCESS read-only
	STATUS mandatory
	DESCRIPTION
		"The firmware revision of the UPS system"
	::= { upsIV3pStrInfo 3 }

upsIV3pRateInputVol OBJECT-TYPE
	SYNTAX INTEGER
	UNITS     "0.01 V"
	ACCESS read-only
	STATUS mandatory
	DESCRIPTION
		"The Rate Input voltage of the UPS system"
	::= { upsIV3pStrInfo 4 }

upsIV3pRateCurrent OBJECT-TYPE
	SYNTAX INTEGER
	UNITS     "0.01 A"
	ACCESS read-only
	STATUS mandatory
	DESCRIPTION
		"The Rate Current of the UPS system"
	::= { upsIV3pStrInfo 5 }

upsIV3pRateBatVol OBJECT-TYPE
	SYNTAX INTEGER
	UNITS     "0.01 V"
	ACCESS read-only
	STATUS mandatory
	DESCRIPTION
		"The Rate battery voltage of the UPS system"
	::= { upsIV3pStrInfo 6 }

upsIV3pRateFre OBJECT-TYPE
	SYNTAX INTEGER
	UNITS     "0.01 Hz"
	ACCESS read-only
	STATUS mandatory
	DESCRIPTION
		"The Rate Frequency of the UPS system"
	::= { upsIV3pStrInfo 7 }
	  
-- ****************************ups3pTraps************************************
-- Traps

upsIII3ppAlarmAdd NOTIFICATION-TYPE
	STATUS      current
	DESCRIPTION
		 "SEVERE: Alarm occur!"
	::= { ups3pTraps 100 }

upsIII3ppAlarmRemove NOTIFICATION-TYPE
	STATUS      current
	DESCRIPTION
		 "SEVERE: Alarm cancel!"
	::= { ups3pTraps 101 }       
END
