--General_Precision_Distribution82-MIB { iso(1) org(3) dod(6) internet(1) private(4)
--      enterprises(1) rcmib(953) }


General_Precision_Distribution82-MIB DEFINITIONS ::= BEGIN
-- Title: PPC TOP LEVEL MIB
-- Date: January 07, 1994    Version 1.00
--
-- Date: January 17, 1994    Version 1.01
--
-- Date: July 14, 1994    Version 1.02


IMPORTS
	enterprises, IpAddress
		FROM RFC1155-SMI
	DisplayString
		FROM RFC1213-MIB
	OBJECT-TYPE
		FROM RFC-1212
	TRAP-TYPE
		FROM RFC-1215;

General_Precision_Distribution82                           OBJECT IDENTIFIER ::=  { enterprises 953 }

FirstGeneral_Precision_Distribution82 OBJECT IDENTIFIER ::=  { General_Precision_Distribution82 1}
FirstGeneral_Precision_Distribution82Analog                       OBJECT IDENTIFIER ::=  { FirstGeneral_Precision_Distribution82 1 }
FirstGeneral_Precision_Distribution82Status                       OBJECT IDENTIFIER ::=  { FirstGeneral_Precision_Distribution82 2 }
FirstGeneral_Precision_Distribution82Alarm                       OBJECT IDENTIFIER ::=  { FirstGeneral_Precision_Distribution82 3 }
General_Precision_Distribution82AlarmTrap                       OBJECT IDENTIFIER ::=  { General_Precision_Distribution82 32 }



-- the General_Precision_Distribution82Analog group
--addGeneral_Precision_Distribution82Analog
First_I_Road_A_phase_voltage OBJECT-TYPE
	SYNTAX INTEGER
	UNITS     "0.01V "
	ACCESS read-only
	STATUS mandatory
	DESCRIPTION
		"First_I_Road_A_phase_voltage"
	::= { FirstGeneral_Precision_Distribution82Analog 1 }
First_I_Road_B_phase_voltage OBJECT-TYPE
	SYNTAX INTEGER
	UNITS     "0.01V "
	ACCESS read-only
	STATUS mandatory
	DESCRIPTION
		"First_I_Road_B_phase_voltage"
	::= { FirstGeneral_Precision_Distribution82Analog 2 }
First_I_Road_C_phase_voltage OBJECT-TYPE
	SYNTAX INTEGER
	UNITS     "0.01V "
	ACCESS read-only
	STATUS mandatory
	DESCRIPTION
		"First_I_Road_C_phase_voltage"
	::= { FirstGeneral_Precision_Distribution82Analog 3 }
First_I_Road_A_phase_current OBJECT-TYPE
	SYNTAX INTEGER
	UNITS     "0.01A "
	ACCESS read-only
	STATUS mandatory
	DESCRIPTION
		"First_I_Road_A_phase_current"
	::= { FirstGeneral_Precision_Distribution82Analog 4 }
First_I_Road_B_phase_current OBJECT-TYPE
	SYNTAX INTEGER
	UNITS     "0.01A "
	ACCESS read-only
	STATUS mandatory
	DESCRIPTION
		"First_I_Road_B_phase_current"
	::= { FirstGeneral_Precision_Distribution82Analog 5 }
First_I_Road_C_phase_current OBJECT-TYPE
	SYNTAX INTEGER
	UNITS     "0.01A "
	ACCESS read-only
	STATUS mandatory
	DESCRIPTION
		"First_I_Road_C_phase_current"
	::= { FirstGeneral_Precision_Distribution82Analog 6 }
First_I_Road_Uab_line_voltage OBJECT-TYPE
	SYNTAX INTEGER
	UNITS     "0.01V "
	ACCESS read-only
	STATUS mandatory
	DESCRIPTION
		"First_I_Road_Uab_line_voltage"
	::= { FirstGeneral_Precision_Distribution82Analog 7 }
First_I_Road_Ubc_line_voltage OBJECT-TYPE
	SYNTAX INTEGER
	UNITS     "0.01V "
	ACCESS read-only
	STATUS mandatory
	DESCRIPTION
		"First_I_Road_Ubc_line_voltage"
	::= { FirstGeneral_Precision_Distribution82Analog 8 }
First_I_Road_Uca_line_voltage OBJECT-TYPE
	SYNTAX INTEGER
	UNITS     "0.01V "
	ACCESS read-only
	STATUS mandatory
	DESCRIPTION
		"First_I_Road_Uca_line_voltage"
	::= { FirstGeneral_Precision_Distribution82Analog 9 }
First_I_Road_A_phase_active_power OBJECT-TYPE
	SYNTAX INTEGER
	UNITS     "0.01KW "
	ACCESS read-only
	STATUS mandatory
	DESCRIPTION
		"First_I_Road_A_phase_active_power"
	::= { FirstGeneral_Precision_Distribution82Analog 10 }
First_I_Road_B_phase_active_power OBJECT-TYPE
	SYNTAX INTEGER
	UNITS     "0.01KW "
	ACCESS read-only
	STATUS mandatory
	DESCRIPTION
		"First_I_Road_B_phase_active_power"
	::= { FirstGeneral_Precision_Distribution82Analog 11 }
First_I_Road_C_phase_active_power OBJECT-TYPE
	SYNTAX INTEGER
	UNITS     "0.01KW "
	ACCESS read-only
	STATUS mandatory
	DESCRIPTION
		"First_I_Road_C_phase_active_power"
	::= { FirstGeneral_Precision_Distribution82Analog 12 }
First_I_Road_A_phase_reactive_power OBJECT-TYPE
	SYNTAX INTEGER
	UNITS     "0.01Kvar "
	ACCESS read-only
	STATUS mandatory
	DESCRIPTION
		"First_I_Road_A_phase_reactive_power"
	::= { FirstGeneral_Precision_Distribution82Analog 13 }
First_I_Road_B_phase_reactive_power OBJECT-TYPE
	SYNTAX INTEGER
	UNITS     "0.01Kvar "
	ACCESS read-only
	STATUS mandatory
	DESCRIPTION
		"First_I_Road_B_phase_reactive_power"
	::= { FirstGeneral_Precision_Distribution82Analog 14 }
First_I_Road_C_phase_reactive_power OBJECT-TYPE
	SYNTAX INTEGER
	UNITS     "0.01Kvar "
	ACCESS read-only
	STATUS mandatory
	DESCRIPTION
		"First_I_Road_C_phase_reactive_power"
	::= { FirstGeneral_Precision_Distribution82Analog 15 }
First_I_Road_A_Apparent_Power OBJECT-TYPE
	SYNTAX INTEGER
	UNITS     "0.01KVA "
	ACCESS read-only
	STATUS mandatory
	DESCRIPTION
		"First_I_Road_A_Apparent_Power"
	::= { FirstGeneral_Precision_Distribution82Analog 16 }
First_I_Road_B_Apparent_Power OBJECT-TYPE
	SYNTAX INTEGER
	UNITS     "0.01KVA "
	ACCESS read-only
	STATUS mandatory
	DESCRIPTION
		"First_I_Road_B_Apparent_Power"
	::= { FirstGeneral_Precision_Distribution82Analog 17 }
First_I_Road_C_Apparent_Power OBJECT-TYPE
	SYNTAX INTEGER
	UNITS     "0.01KVA "
	ACCESS read-only
	STATUS mandatory
	DESCRIPTION
		"First_I_Road_C_Apparent_Power"
	::= { FirstGeneral_Precision_Distribution82Analog 18 }
First_I_Road_A_phase_power_factor OBJECT-TYPE
	SYNTAX INTEGER
	UNITS     "0.01 "
	ACCESS read-only
	STATUS mandatory
	DESCRIPTION
		"First_I_Road_A_phase_power_factor"
	::= { FirstGeneral_Precision_Distribution82Analog 19 }
First_I_Road_B_phase_power_factor OBJECT-TYPE
	SYNTAX INTEGER
	UNITS     "0.01 "
	ACCESS read-only
	STATUS mandatory
	DESCRIPTION
		"First_I_Road_B_phase_power_factor"
	::= { FirstGeneral_Precision_Distribution82Analog 20 }
First_I_Road_C_phase_power_factor OBJECT-TYPE
	SYNTAX INTEGER
	UNITS     "0.01 "
	ACCESS read-only
	STATUS mandatory
	DESCRIPTION
		"First_I_Road_C_phase_power_factor"
	::= { FirstGeneral_Precision_Distribution82Analog 21 }
First_I_road_A_phase_power OBJECT-TYPE
	SYNTAX INTEGER
	UNITS     "0.01KWh "
	ACCESS read-only
	STATUS mandatory
	DESCRIPTION
		"First_I_road_A_phase_power"
	::= { FirstGeneral_Precision_Distribution82Analog 22 }
First_I_Road_B_Phase_Power OBJECT-TYPE
	SYNTAX INTEGER
	UNITS     "0.01KWh "
	ACCESS read-only
	STATUS mandatory
	DESCRIPTION
		"First_I_Road_B_Phase_Power"
	::= { FirstGeneral_Precision_Distribution82Analog 23 }
First_I_Road_C_phase_power OBJECT-TYPE
	SYNTAX INTEGER
	UNITS     "0.01KWh "
	ACCESS read-only
	STATUS mandatory
	DESCRIPTION
		"First_I_Road_C_phase_power"
	::= { FirstGeneral_Precision_Distribution82Analog 24 }
First_I_Road_A_phase_voltage_percentage OBJECT-TYPE
	SYNTAX INTEGER
	UNITS     "0.01% "
	ACCESS read-only
	STATUS mandatory
	DESCRIPTION
		"First_I_Road_A_phase_voltage_percentage"
	::= { FirstGeneral_Precision_Distribution82Analog 25 }
First_I_Road_B_phase_voltage_percentage OBJECT-TYPE
	SYNTAX INTEGER
	UNITS     "0.01% "
	ACCESS read-only
	STATUS mandatory
	DESCRIPTION
		"First_I_Road_B_phase_voltage_percentage"
	::= { FirstGeneral_Precision_Distribution82Analog 26 }
First_I_Road_C_phase_voltage_percentage OBJECT-TYPE
	SYNTAX INTEGER
	UNITS     "0.01% "
	ACCESS read-only
	STATUS mandatory
	DESCRIPTION
		"First_I_Road_C_phase_voltage_percentage"
	::= { FirstGeneral_Precision_Distribution82Analog 27 }
First_I_Road_A_phase_current_percentage OBJECT-TYPE
	SYNTAX INTEGER
	UNITS     "0.01% "
	ACCESS read-only
	STATUS mandatory
	DESCRIPTION
		"First_I_Road_A_phase_current_percentage"
	::= { FirstGeneral_Precision_Distribution82Analog 28 }
First_I_Road_B_phase_current_percentage OBJECT-TYPE
	SYNTAX INTEGER
	UNITS     "0.01% "
	ACCESS read-only
	STATUS mandatory
	DESCRIPTION
		"First_I_Road_B_phase_current_percentage"
	::= { FirstGeneral_Precision_Distribution82Analog 29 }
First_I_Road_C_phase_current_percentage OBJECT-TYPE
	SYNTAX INTEGER
	UNITS     "0.01% "
	ACCESS read-only
	STATUS mandatory
	DESCRIPTION
		"First_I_Road_C_phase_current_percentage"
	::= { FirstGeneral_Precision_Distribution82Analog 30 }
First_I_Road_A_phase_rated_current OBJECT-TYPE
	SYNTAX INTEGER
	UNITS     "0.01A "
	ACCESS read-only
	STATUS mandatory
	DESCRIPTION
		"First_I_Road_A_phase_rated_current"
	::= { FirstGeneral_Precision_Distribution82Analog 31 }
First_I_Road_B_phase_rated_current OBJECT-TYPE
	SYNTAX INTEGER
	UNITS     "0.01A "
	ACCESS read-only
	STATUS mandatory
	DESCRIPTION
		"First_I_Road_B_phase_rated_current"
	::= { FirstGeneral_Precision_Distribution82Analog 32 }
First_I_Road_C_phase_rated_current OBJECT-TYPE
	SYNTAX INTEGER
	UNITS     "0.01A "
	ACCESS read-only
	STATUS mandatory
	DESCRIPTION
		"First_I_Road_C_phase_rated_current"
	::= { FirstGeneral_Precision_Distribution82Analog 33 }
First_I_Road_Rated_frequency OBJECT-TYPE
	SYNTAX INTEGER
	UNITS     "0.01Hz "
	ACCESS read-only
	STATUS mandatory
	DESCRIPTION
		"First_I_Road_Rated_frequency"
	::= { FirstGeneral_Precision_Distribution82Analog 34 }
First_I_Road_Rated_voltage OBJECT-TYPE
	SYNTAX INTEGER
	UNITS     "0.01V "
	ACCESS read-only
	STATUS mandatory
	DESCRIPTION
		"First_I_Road_Rated_voltage"
	::= { FirstGeneral_Precision_Distribution82Analog 35 }
First_I_Road_Rated_capacity OBJECT-TYPE
	SYNTAX INTEGER
	UNITS     "0.01% "
	ACCESS read-only
	STATUS mandatory
	DESCRIPTION
		"First_I_Road_Rated_capacity"
	::= { FirstGeneral_Precision_Distribution82Analog 36 }
First_I_Road_voltage_ratio OBJECT-TYPE
	SYNTAX INTEGER
	UNITS     "0.01 "
	ACCESS read-only
	STATUS mandatory
	DESCRIPTION
		"First_I_Road_voltage_ratio"
	::= { FirstGeneral_Precision_Distribution82Analog 37 }
First_I_Road_current_ratio OBJECT-TYPE
	SYNTAX INTEGER
	UNITS     "0.01 "
	ACCESS read-only
	STATUS mandatory
	DESCRIPTION
		"First_I_Road_current_ratio"
	::= { FirstGeneral_Precision_Distribution82Analog 38 }
First_I_Road_line_zero_current OBJECT-TYPE
	SYNTAX INTEGER
	UNITS     "0.01A "
	ACCESS read-only
	STATUS mandatory
	DESCRIPTION
		"First_I_Road_line_zero_current"
	::= { FirstGeneral_Precision_Distribution82Analog 39 }
First_I_Road_line_zero_voltage OBJECT-TYPE
	SYNTAX INTEGER
	UNITS     "0.01V "
	ACCESS read-only
	STATUS mandatory
	DESCRIPTION
		"First_I_Road_line_zero_voltage"
	::= { FirstGeneral_Precision_Distribution82Analog 40 }
First_I_Road_main_road_temperature OBJECT-TYPE
	SYNTAX INTEGER
	UNITS     "0.01℃ "
	ACCESS read-only
	STATUS mandatory
	DESCRIPTION
		"First_I_Road_main_road_temperature"
	::= { FirstGeneral_Precision_Distribution82Analog 41 }
First_I_Road_A_phase_voltage_harmonics OBJECT-TYPE
	SYNTAX INTEGER
	UNITS     "0.01% "
	ACCESS read-only
	STATUS mandatory
	DESCRIPTION
		"First_I_Road_A_phase_voltage_harmonics"
	::= { FirstGeneral_Precision_Distribution82Analog 42 }
First_I_Road_B_phase_voltage_harmonics OBJECT-TYPE
	SYNTAX INTEGER
	UNITS     "0.01% "
	ACCESS read-only
	STATUS mandatory
	DESCRIPTION
		"First_I_Road_B_phase_voltage_harmonics"
	::= { FirstGeneral_Precision_Distribution82Analog 43 }
First_I_Road_C_phase_voltage_harmonics OBJECT-TYPE
	SYNTAX INTEGER
	UNITS     "0.01% "
	ACCESS read-only
	STATUS mandatory
	DESCRIPTION
		"First_I_Road_C_phase_voltage_harmonics"
	::= { FirstGeneral_Precision_Distribution82Analog 44 }
First_I_Road_A_phase_current_harmonics OBJECT-TYPE
	SYNTAX INTEGER
	UNITS     "0.01% "
	ACCESS read-only
	STATUS mandatory
	DESCRIPTION
		"First_I_Road_A_phase_current_harmonics"
	::= { FirstGeneral_Precision_Distribution82Analog 45 }
First_I_Road_B_phase_current_harmonics OBJECT-TYPE
	SYNTAX INTEGER
	UNITS     "0.01% "
	ACCESS read-only
	STATUS mandatory
	DESCRIPTION
		"First_I_Road_B_phase_current_harmonics"
	::= { FirstGeneral_Precision_Distribution82Analog 46 }
First_I_Road_C_Road_current_harmonics OBJECT-TYPE
	SYNTAX INTEGER
	UNITS     "0.01% "
	ACCESS read-only
	STATUS mandatory
	DESCRIPTION
		"First_I_Road_C_Road_current_harmonics"
	::= { FirstGeneral_Precision_Distribution82Analog 47 }
First_I_Road_frequency OBJECT-TYPE
	SYNTAX INTEGER
	UNITS     "0.01Hz "
	ACCESS read-only
	STATUS mandatory
	DESCRIPTION
		"First_I_Road_frequency"
	::= { FirstGeneral_Precision_Distribution82Analog 48 }
First_I_Road_total_active_energy OBJECT-TYPE
	SYNTAX INTEGER
	UNITS     "0.01KWh "
	ACCESS read-only
	STATUS mandatory
	DESCRIPTION
		"First_I_Road_total_active_energy"
	::= { FirstGeneral_Precision_Distribution82Analog 49 }
First_I_Road_total_reactive_energy OBJECT-TYPE
	SYNTAX INTEGER
	UNITS     "0.01kvarh "
	ACCESS read-only
	STATUS mandatory
	DESCRIPTION
		"First_I_Road_total_reactive_energy"
	::= { FirstGeneral_Precision_Distribution82Analog 50 }
First_II_Road_A_phase_voltage OBJECT-TYPE
	SYNTAX INTEGER
	UNITS     "0.01V "
	ACCESS read-only
	STATUS mandatory
	DESCRIPTION
		"First_II_Road_A_phase_voltage"
	::= { FirstGeneral_Precision_Distribution82Analog 51 }
First_II_Road_B_phase_voltage OBJECT-TYPE
	SYNTAX INTEGER
	UNITS     "0.01V "
	ACCESS read-only
	STATUS mandatory
	DESCRIPTION
		"First_II_Road_B_phase_voltage"
	::= { FirstGeneral_Precision_Distribution82Analog 52 }
First_II_Road_C_phase_voltage OBJECT-TYPE
	SYNTAX INTEGER
	UNITS     "0.01V "
	ACCESS read-only
	STATUS mandatory
	DESCRIPTION
		"First_II_Road_C_phase_voltage"
	::= { FirstGeneral_Precision_Distribution82Analog 53 }
First_II_Road_A_phase_current OBJECT-TYPE
	SYNTAX INTEGER
	UNITS     "0.01A "
	ACCESS read-only
	STATUS mandatory
	DESCRIPTION
		"First_II_Road_A_phase_current"
	::= { FirstGeneral_Precision_Distribution82Analog 54 }
First_II_Road_B_phase_current OBJECT-TYPE
	SYNTAX INTEGER
	UNITS     "0.01A "
	ACCESS read-only
	STATUS mandatory
	DESCRIPTION
		"First_II_Road_B_phase_current"
	::= { FirstGeneral_Precision_Distribution82Analog 55 }
First_II_Road_C_phase_current OBJECT-TYPE
	SYNTAX INTEGER
	UNITS     "0.01A "
	ACCESS read-only
	STATUS mandatory
	DESCRIPTION
		"First_II_Road_C_phase_current"
	::= { FirstGeneral_Precision_Distribution82Analog 56 }
First_II_Road_Uab_line_voltage OBJECT-TYPE
	SYNTAX INTEGER
	UNITS     "0.01V "
	ACCESS read-only
	STATUS mandatory
	DESCRIPTION
		"First_II_Road_Uab_line_voltage"
	::= { FirstGeneral_Precision_Distribution82Analog 57 }
First_II_Road_Ubc_line_voltage OBJECT-TYPE
	SYNTAX INTEGER
	UNITS     "0.01V "
	ACCESS read-only
	STATUS mandatory
	DESCRIPTION
		"First_II_Road_Ubc_line_voltage"
	::= { FirstGeneral_Precision_Distribution82Analog 58 }
First_II_Road_Uca_line_voltage OBJECT-TYPE
	SYNTAX INTEGER
	UNITS     "0.01V "
	ACCESS read-only
	STATUS mandatory
	DESCRIPTION
		"First_II_Road_Uca_line_voltage"
	::= { FirstGeneral_Precision_Distribution82Analog 59 }
First_II_Road_A_phase_active_power OBJECT-TYPE
	SYNTAX INTEGER
	UNITS     "0.01KW "
	ACCESS read-only
	STATUS mandatory
	DESCRIPTION
		"First_II_Road_A_phase_active_power"
	::= { FirstGeneral_Precision_Distribution82Analog 60 }
First_II_Road_B_phase_active_power OBJECT-TYPE
	SYNTAX INTEGER
	UNITS     "0.01KW "
	ACCESS read-only
	STATUS mandatory
	DESCRIPTION
		"First_II_Road_B_phase_active_power"
	::= { FirstGeneral_Precision_Distribution82Analog 61 }
First_II_Road_C_phase_active_power OBJECT-TYPE
	SYNTAX INTEGER
	UNITS     "0.01KW "
	ACCESS read-only
	STATUS mandatory
	DESCRIPTION
		"First_II_Road_C_phase_active_power"
	::= { FirstGeneral_Precision_Distribution82Analog 62 }
First_II_Road_A_phase_reactive_power OBJECT-TYPE
	SYNTAX INTEGER
	UNITS     "0.01Kvar "
	ACCESS read-only
	STATUS mandatory
	DESCRIPTION
		"First_II_Road_A_phase_reactive_power"
	::= { FirstGeneral_Precision_Distribution82Analog 63 }
First_II_Road_B_phase_reactive_power OBJECT-TYPE
	SYNTAX INTEGER
	UNITS     "0.01Kvar "
	ACCESS read-only
	STATUS mandatory
	DESCRIPTION
		"First_II_Road_B_phase_reactive_power"
	::= { FirstGeneral_Precision_Distribution82Analog 64 }
First_II_Road_C_phase_reactive_power OBJECT-TYPE
	SYNTAX INTEGER
	UNITS     "0.01Kvar "
	ACCESS read-only
	STATUS mandatory
	DESCRIPTION
		"First_II_Road_C_phase_reactive_power"
	::= { FirstGeneral_Precision_Distribution82Analog 65 }
First_II_Road_A_Apparent_Power OBJECT-TYPE
	SYNTAX INTEGER
	UNITS     "0.01KVA "
	ACCESS read-only
	STATUS mandatory
	DESCRIPTION
		"First_II_Road_A_Apparent_Power"
	::= { FirstGeneral_Precision_Distribution82Analog 66 }
First_II_Road_B_Apparent_Power OBJECT-TYPE
	SYNTAX INTEGER
	UNITS     "0.01KVA "
	ACCESS read-only
	STATUS mandatory
	DESCRIPTION
		"First_II_Road_B_Apparent_Power"
	::= { FirstGeneral_Precision_Distribution82Analog 67 }
First_II_Road_C_Apparent_Power OBJECT-TYPE
	SYNTAX INTEGER
	UNITS     "0.01KVA "
	ACCESS read-only
	STATUS mandatory
	DESCRIPTION
		"First_II_Road_C_Apparent_Power"
	::= { FirstGeneral_Precision_Distribution82Analog 68 }
First_II_Road_A_phase_power_factor OBJECT-TYPE
	SYNTAX INTEGER
	UNITS     "0.01 "
	ACCESS read-only
	STATUS mandatory
	DESCRIPTION
		"First_II_Road_A_phase_power_factor"
	::= { FirstGeneral_Precision_Distribution82Analog 69 }
First_II_Road_B_phase_power_factor OBJECT-TYPE
	SYNTAX INTEGER
	UNITS     "0.01 "
	ACCESS read-only
	STATUS mandatory
	DESCRIPTION
		"First_II_Road_B_phase_power_factor"
	::= { FirstGeneral_Precision_Distribution82Analog 70 }
First_II_Road_C_phase_power_factor OBJECT-TYPE
	SYNTAX INTEGER
	UNITS     "0.01 "
	ACCESS read-only
	STATUS mandatory
	DESCRIPTION
		"First_II_Road_C_phase_power_factor"
	::= { FirstGeneral_Precision_Distribution82Analog 71 }
First_II_road_A_phase_power OBJECT-TYPE
	SYNTAX INTEGER
	UNITS     "0.01KWh "
	ACCESS read-only
	STATUS mandatory
	DESCRIPTION
		"First_II_road_A_phase_power"
	::= { FirstGeneral_Precision_Distribution82Analog 72 }
First_II_Road_B_Phase_Power OBJECT-TYPE
	SYNTAX INTEGER
	UNITS     "0.01KWh "
	ACCESS read-only
	STATUS mandatory
	DESCRIPTION
		"First_II_Road_B_Phase_Power"
	::= { FirstGeneral_Precision_Distribution82Analog 73 }
First_II_Road_C_phase_power OBJECT-TYPE
	SYNTAX INTEGER
	UNITS     "0.01KWh "
	ACCESS read-only
	STATUS mandatory
	DESCRIPTION
		"First_II_Road_C_phase_power"
	::= { FirstGeneral_Precision_Distribution82Analog 74 }
First_II_Road_A_phase_voltage_percentage OBJECT-TYPE
	SYNTAX INTEGER
	UNITS     "0.01% "
	ACCESS read-only
	STATUS mandatory
	DESCRIPTION
		"First_II_Road_A_phase_voltage_percentage"
	::= { FirstGeneral_Precision_Distribution82Analog 75 }
First_II_Road_B_phase_voltage_percentage OBJECT-TYPE
	SYNTAX INTEGER
	UNITS     "0.01% "
	ACCESS read-only
	STATUS mandatory
	DESCRIPTION
		"First_II_Road_B_phase_voltage_percentage"
	::= { FirstGeneral_Precision_Distribution82Analog 76 }
First_II_Road_C_phase_voltage_percentage OBJECT-TYPE
	SYNTAX INTEGER
	UNITS     "0.01% "
	ACCESS read-only
	STATUS mandatory
	DESCRIPTION
		"First_II_Road_C_phase_voltage_percentage"
	::= { FirstGeneral_Precision_Distribution82Analog 77 }
First_II_Road_A_phase_current_percentage OBJECT-TYPE
	SYNTAX INTEGER
	UNITS     "0.01% "
	ACCESS read-only
	STATUS mandatory
	DESCRIPTION
		"First_II_Road_A_phase_current_percentage"
	::= { FirstGeneral_Precision_Distribution82Analog 78 }
First_II_Road_B_phase_current_percentage OBJECT-TYPE
	SYNTAX INTEGER
	UNITS     "0.01% "
	ACCESS read-only
	STATUS mandatory
	DESCRIPTION
		"First_II_Road_B_phase_current_percentage"
	::= { FirstGeneral_Precision_Distribution82Analog 79 }
First_II_Road_C_phase_current_percentage OBJECT-TYPE
	SYNTAX INTEGER
	UNITS     "0.01% "
	ACCESS read-only
	STATUS mandatory
	DESCRIPTION
		"First_II_Road_C_phase_current_percentage"
	::= { FirstGeneral_Precision_Distribution82Analog 80 }
First_II_Road_A_phase_rated_current OBJECT-TYPE
	SYNTAX INTEGER
	UNITS     "0.01A "
	ACCESS read-only
	STATUS mandatory
	DESCRIPTION
		"First_II_Road_A_phase_rated_current"
	::= { FirstGeneral_Precision_Distribution82Analog 81 }
First_II_Road_B_phase_rated_current OBJECT-TYPE
	SYNTAX INTEGER
	UNITS     "0.01A "
	ACCESS read-only
	STATUS mandatory
	DESCRIPTION
		"First_II_Road_B_phase_rated_current"
	::= { FirstGeneral_Precision_Distribution82Analog 82 }
First_II_Road_C_phase_rated_current OBJECT-TYPE
	SYNTAX INTEGER
	UNITS     "0.01A "
	ACCESS read-only
	STATUS mandatory
	DESCRIPTION
		"First_II_Road_C_phase_rated_current"
	::= { FirstGeneral_Precision_Distribution82Analog 83 }
First_II_Road_Rated_frequency OBJECT-TYPE
	SYNTAX INTEGER
	UNITS     "0.01Hz "
	ACCESS read-only
	STATUS mandatory
	DESCRIPTION
		"First_II_Road_Rated_frequency"
	::= { FirstGeneral_Precision_Distribution82Analog 84 }
First_II_Road_Rated_voltage OBJECT-TYPE
	SYNTAX INTEGER
	UNITS     "0.01V "
	ACCESS read-only
	STATUS mandatory
	DESCRIPTION
		"First_II_Road_Rated_voltage"
	::= { FirstGeneral_Precision_Distribution82Analog 85 }
First_II_Road_Rated_capacity OBJECT-TYPE
	SYNTAX INTEGER
	UNITS     "0.01% "
	ACCESS read-only
	STATUS mandatory
	DESCRIPTION
		"First_II_Road_Rated_capacity"
	::= { FirstGeneral_Precision_Distribution82Analog 86 }
First_II_Road_voltage_ratio OBJECT-TYPE
	SYNTAX INTEGER
	UNITS     "0.01 "
	ACCESS read-only
	STATUS mandatory
	DESCRIPTION
		"First_II_Road_voltage_ratio"
	::= { FirstGeneral_Precision_Distribution82Analog 87 }
First_II_Road_current_ratio OBJECT-TYPE
	SYNTAX INTEGER
	UNITS     "0.01 "
	ACCESS read-only
	STATUS mandatory
	DESCRIPTION
		"First_II_Road_current_ratio"
	::= { FirstGeneral_Precision_Distribution82Analog 88 }
First_II_Road_line_zero_current OBJECT-TYPE
	SYNTAX INTEGER
	UNITS     "0.01A "
	ACCESS read-only
	STATUS mandatory
	DESCRIPTION
		"First_II_Road_line_zero_current"
	::= { FirstGeneral_Precision_Distribution82Analog 89 }
First_II_Road_line_zero_voltage OBJECT-TYPE
	SYNTAX INTEGER
	UNITS     "0.01V "
	ACCESS read-only
	STATUS mandatory
	DESCRIPTION
		"First_II_Road_line_zero_voltage"
	::= { FirstGeneral_Precision_Distribution82Analog 90 }
First_II_Road_main_road_temperature OBJECT-TYPE
	SYNTAX INTEGER
	UNITS     "0.01℃ "
	ACCESS read-only
	STATUS mandatory
	DESCRIPTION
		"First_II_Road_main_road_temperature"
	::= { FirstGeneral_Precision_Distribution82Analog 91 }
First_II_Road_A_phase_voltage_harmonics OBJECT-TYPE
	SYNTAX INTEGER
	UNITS     "0.01% "
	ACCESS read-only
	STATUS mandatory
	DESCRIPTION
		"First_II_Road_A_phase_voltage_harmonics"
	::= { FirstGeneral_Precision_Distribution82Analog 92 }
First_II_Road_B_phase_voltage_harmonics OBJECT-TYPE
	SYNTAX INTEGER
	UNITS     "0.01% "
	ACCESS read-only
	STATUS mandatory
	DESCRIPTION
		"First_II_Road_B_phase_voltage_harmonics"
	::= { FirstGeneral_Precision_Distribution82Analog 93 }
First_II_Road_C_phase_voltage_harmonics OBJECT-TYPE
	SYNTAX INTEGER
	UNITS     "0.01% "
	ACCESS read-only
	STATUS mandatory
	DESCRIPTION
		"First_II_Road_C_phase_voltage_harmonics"
	::= { FirstGeneral_Precision_Distribution82Analog 94 }
First_II_Road_A_phase_current_harmonics OBJECT-TYPE
	SYNTAX INTEGER
	UNITS     "0.01% "
	ACCESS read-only
	STATUS mandatory
	DESCRIPTION
		"First_II_Road_A_phase_current_harmonics"
	::= { FirstGeneral_Precision_Distribution82Analog 95 }
First_II_Road_B_phase_current_harmonics OBJECT-TYPE
	SYNTAX INTEGER
	UNITS     "0.01% "
	ACCESS read-only
	STATUS mandatory
	DESCRIPTION
		"First_II_Road_B_phase_current_harmonics"
	::= { FirstGeneral_Precision_Distribution82Analog 96 }
First_II_Road_C_Road_current_harmonics OBJECT-TYPE
	SYNTAX INTEGER
	UNITS     "0.01% "
	ACCESS read-only
	STATUS mandatory
	DESCRIPTION
		"First_II_Road_C_Road_current_harmonics"
	::= { FirstGeneral_Precision_Distribution82Analog 97 }
First_II_Road_frequency OBJECT-TYPE
	SYNTAX INTEGER
	UNITS     "0.01Hz "
	ACCESS read-only
	STATUS mandatory
	DESCRIPTION
		"First_II_Road_frequency"
	::= { FirstGeneral_Precision_Distribution82Analog 98 }
First_II_Road_total_active_energy OBJECT-TYPE
	SYNTAX INTEGER
	UNITS     "0.01KWh "
	ACCESS read-only
	STATUS mandatory
	DESCRIPTION
		"First_II_Road_total_active_energy"
	::= { FirstGeneral_Precision_Distribution82Analog 99 }
First_II_Road_total_reactive_energy OBJECT-TYPE
	SYNTAX INTEGER
	UNITS     "0.01kvarh "
	ACCESS read-only
	STATUS mandatory
	DESCRIPTION
		"First_II_Road_total_reactive_energy"
	::= { FirstGeneral_Precision_Distribution82Analog 100 }
First_source_1_branch_1_output_voltage OBJECT-TYPE
	SYNTAX INTEGER
	UNITS     "0.01V "
	ACCESS read-only
	STATUS mandatory
	DESCRIPTION
		"First_source_1_branch_1_output_voltage"
	::= { FirstGeneral_Precision_Distribution82Analog 101 }
First_source_1_branch_2_output_voltage OBJECT-TYPE
	SYNTAX INTEGER
	UNITS     "0.01 "
	ACCESS read-only
	STATUS mandatory
	DESCRIPTION
		"First_source_1_branch_2_output_voltage"
	::= { FirstGeneral_Precision_Distribution82Analog 102 }
First_source_1_branch_3_output_voltage OBJECT-TYPE
	SYNTAX INTEGER
	UNITS     "0.01 "
	ACCESS read-only
	STATUS mandatory
	DESCRIPTION
		"First_source_1_branch_3_output_voltage"
	::= { FirstGeneral_Precision_Distribution82Analog 103 }
First_source_1_branch_4_output_voltage OBJECT-TYPE
	SYNTAX INTEGER
	UNITS     "0.01 "
	ACCESS read-only
	STATUS mandatory
	DESCRIPTION
		"First_source_1_branch_4_output_voltage"
	::= { FirstGeneral_Precision_Distribution82Analog 104 }
First_source_1_branch_5_output_voltage OBJECT-TYPE
	SYNTAX INTEGER
	UNITS     "0.01 "
	ACCESS read-only
	STATUS mandatory
	DESCRIPTION
		"First_source_1_branch_5_output_voltage"
	::= { FirstGeneral_Precision_Distribution82Analog 105 }
First_source_1_branch_6_output_voltage OBJECT-TYPE
	SYNTAX INTEGER
	UNITS     "0.01 "
	ACCESS read-only
	STATUS mandatory
	DESCRIPTION
		"First_source_1_branch_6_output_voltage"
	::= { FirstGeneral_Precision_Distribution82Analog 106 }
First_source_1_branch_7_output_voltage OBJECT-TYPE
	SYNTAX INTEGER
	UNITS     "0.01 "
	ACCESS read-only
	STATUS mandatory
	DESCRIPTION
		"First_source_1_branch_7_output_voltage"
	::= { FirstGeneral_Precision_Distribution82Analog 107 }
First_source_1_branch_8_output_voltage OBJECT-TYPE
	SYNTAX INTEGER
	UNITS     "0.01 "
	ACCESS read-only
	STATUS mandatory
	DESCRIPTION
		"First_source_1_branch_8_output_voltage"
	::= { FirstGeneral_Precision_Distribution82Analog 108 }
First_source_1_branch_9_output_voltage OBJECT-TYPE
	SYNTAX INTEGER
	UNITS     "0.01 "
	ACCESS read-only
	STATUS mandatory
	DESCRIPTION
		"First_source_1_branch_9_output_voltage"
	::= { FirstGeneral_Precision_Distribution82Analog 109 }
First_source_1_branch_10_output_voltage OBJECT-TYPE
	SYNTAX INTEGER
	UNITS     "0.01 "
	ACCESS read-only
	STATUS mandatory
	DESCRIPTION
		"First_source_1_branch_10_output_voltage"
	::= { FirstGeneral_Precision_Distribution82Analog 110 }
First_source_1_branch_11_output_voltage OBJECT-TYPE
	SYNTAX INTEGER
	UNITS     "0.01 "
	ACCESS read-only
	STATUS mandatory
	DESCRIPTION
		"First_source_1_branch_11_output_voltage"
	::= { FirstGeneral_Precision_Distribution82Analog 111 }
First_source_1_branch_12_output_voltage OBJECT-TYPE
	SYNTAX INTEGER
	UNITS     "0.01 "
	ACCESS read-only
	STATUS mandatory
	DESCRIPTION
		"First_source_1_branch_12_output_voltage"
	::= { FirstGeneral_Precision_Distribution82Analog 112 }
First_source_1_branch_13_output_voltage OBJECT-TYPE
	SYNTAX INTEGER
	UNITS     "0.01 "
	ACCESS read-only
	STATUS mandatory
	DESCRIPTION
		"First_source_1_branch_13_output_voltage"
	::= { FirstGeneral_Precision_Distribution82Analog 113 }
First_source_1_branch_14_output_voltage OBJECT-TYPE
	SYNTAX INTEGER
	UNITS     "0.01 "
	ACCESS read-only
	STATUS mandatory
	DESCRIPTION
		"First_source_1_branch_14_output_voltage"
	::= { FirstGeneral_Precision_Distribution82Analog 114 }
First_source_1_branch_15_output_voltage OBJECT-TYPE
	SYNTAX INTEGER
	UNITS     "0.01 "
	ACCESS read-only
	STATUS mandatory
	DESCRIPTION
		"First_source_1_branch_15_output_voltage"
	::= { FirstGeneral_Precision_Distribution82Analog 115 }
First_source_1_branch_16_output_voltage OBJECT-TYPE
	SYNTAX INTEGER
	UNITS     "0.01 "
	ACCESS read-only
	STATUS mandatory
	DESCRIPTION
		"First_source_1_branch_16_output_voltage"
	::= { FirstGeneral_Precision_Distribution82Analog 116 }
First_source_1_branch_17_output_voltage OBJECT-TYPE
	SYNTAX INTEGER
	UNITS     "0.01 "
	ACCESS read-only
	STATUS mandatory
	DESCRIPTION
		"First_source_1_branch_17_output_voltage"
	::= { FirstGeneral_Precision_Distribution82Analog 117 }
First_source_1_branch_18_output_voltage OBJECT-TYPE
	SYNTAX INTEGER
	UNITS     "0.01 "
	ACCESS read-only
	STATUS mandatory
	DESCRIPTION
		"First_source_1_branch_18_output_voltage"
	::= { FirstGeneral_Precision_Distribution82Analog 118 }
First_source_1_branch_19_output_voltage OBJECT-TYPE
	SYNTAX INTEGER
	UNITS     "0.01 "
	ACCESS read-only
	STATUS mandatory
	DESCRIPTION
		"First_source_1_branch_19_output_voltage"
	::= { FirstGeneral_Precision_Distribution82Analog 119 }
First_source_1_branch_20_output_voltage OBJECT-TYPE
	SYNTAX INTEGER
	UNITS     "0.01 "
	ACCESS read-only
	STATUS mandatory
	DESCRIPTION
		"First_source_1_branch_20_output_voltage"
	::= { FirstGeneral_Precision_Distribution82Analog 120 }
First_source_1_branch_21_output_voltage OBJECT-TYPE
	SYNTAX INTEGER
	UNITS     "0.01 "
	ACCESS read-only
	STATUS mandatory
	DESCRIPTION
		"First_source_1_branch_21_output_voltage"
	::= { FirstGeneral_Precision_Distribution82Analog 121 }
First_source_1_branch_22_output_voltage OBJECT-TYPE
	SYNTAX INTEGER
	UNITS     "0.01 "
	ACCESS read-only
	STATUS mandatory
	DESCRIPTION
		"First_source_1_branch_22_output_voltage"
	::= { FirstGeneral_Precision_Distribution82Analog 122 }
First_source_1_branch_23_output_voltage OBJECT-TYPE
	SYNTAX INTEGER
	UNITS     "0.01 "
	ACCESS read-only
	STATUS mandatory
	DESCRIPTION
		"First_source_1_branch_23_output_voltage"
	::= { FirstGeneral_Precision_Distribution82Analog 123 }
First_source_1_branch_24_output_voltage OBJECT-TYPE
	SYNTAX INTEGER
	UNITS     "0.01 "
	ACCESS read-only
	STATUS mandatory
	DESCRIPTION
		"First_source_1_branch_24_output_voltage"
	::= { FirstGeneral_Precision_Distribution82Analog 124 }
First_source_1_branch_25_output_voltage OBJECT-TYPE
	SYNTAX INTEGER
	UNITS     "0.01 "
	ACCESS read-only
	STATUS mandatory
	DESCRIPTION
		"First_source_1_branch_25_output_voltage"
	::= { FirstGeneral_Precision_Distribution82Analog 125 }
First_source_1_branch_26_output_voltage OBJECT-TYPE
	SYNTAX INTEGER
	UNITS     "0.01 "
	ACCESS read-only
	STATUS mandatory
	DESCRIPTION
		"First_source_1_branch_26_output_voltage"
	::= { FirstGeneral_Precision_Distribution82Analog 126 }
First_source_1_branch_27_output_voltage OBJECT-TYPE
	SYNTAX INTEGER
	UNITS     "0.01 "
	ACCESS read-only
	STATUS mandatory
	DESCRIPTION
		"First_source_1_branch_27_output_voltage"
	::= { FirstGeneral_Precision_Distribution82Analog 127 }
First_source_1_branch_28_output_voltage OBJECT-TYPE
	SYNTAX INTEGER
	UNITS     "0.01 "
	ACCESS read-only
	STATUS mandatory
	DESCRIPTION
		"First_source_1_branch_28_output_voltage"
	::= { FirstGeneral_Precision_Distribution82Analog 128 }
First_source_1_branch_29_output_voltage OBJECT-TYPE
	SYNTAX INTEGER
	UNITS     "0.01 "
	ACCESS read-only
	STATUS mandatory
	DESCRIPTION
		"First_source_1_branch_29_output_voltage"
	::= { FirstGeneral_Precision_Distribution82Analog 129 }
First_source_1_branch_30_output_voltage OBJECT-TYPE
	SYNTAX INTEGER
	UNITS     "0.01 "
	ACCESS read-only
	STATUS mandatory
	DESCRIPTION
		"First_source_1_branch_30_output_voltage"
	::= { FirstGeneral_Precision_Distribution82Analog 130 }
First_source_1_branch_31_output_voltage OBJECT-TYPE
	SYNTAX INTEGER
	UNITS     "0.01 "
	ACCESS read-only
	STATUS mandatory
	DESCRIPTION
		"First_source_1_branch_31_output_voltage"
	::= { FirstGeneral_Precision_Distribution82Analog 131 }
First_source_1_branch_32_output_voltage OBJECT-TYPE
	SYNTAX INTEGER
	UNITS     "0.01 "
	ACCESS read-only
	STATUS mandatory
	DESCRIPTION
		"First_source_1_branch_32_output_voltage"
	::= { FirstGeneral_Precision_Distribution82Analog 132 }
First_source_1_branch_33_output_voltage OBJECT-TYPE
	SYNTAX INTEGER
	UNITS     "0.01 "
	ACCESS read-only
	STATUS mandatory
	DESCRIPTION
		"First_source_1_branch_33_output_voltage"
	::= { FirstGeneral_Precision_Distribution82Analog 133 }
First_source_1_branch_34_output_voltage OBJECT-TYPE
	SYNTAX INTEGER
	UNITS     "0.01 "
	ACCESS read-only
	STATUS mandatory
	DESCRIPTION
		"First_source_1_branch_34_output_voltage"
	::= { FirstGeneral_Precision_Distribution82Analog 134 }
First_source_1_branch_35_output_voltage OBJECT-TYPE
	SYNTAX INTEGER
	UNITS     "0.01 "
	ACCESS read-only
	STATUS mandatory
	DESCRIPTION
		"First_source_1_branch_35_output_voltage"
	::= { FirstGeneral_Precision_Distribution82Analog 135 }
First_source_1_branch_36_output_voltage OBJECT-TYPE
	SYNTAX INTEGER
	UNITS     "0.01 "
	ACCESS read-only
	STATUS mandatory
	DESCRIPTION
		"First_source_1_branch_36_output_voltage"
	::= { FirstGeneral_Precision_Distribution82Analog 136 }
First_source_1_branch_37_output_voltage OBJECT-TYPE
	SYNTAX INTEGER
	UNITS     "0.01 "
	ACCESS read-only
	STATUS mandatory
	DESCRIPTION
		"First_source_1_branch_37_output_voltage"
	::= { FirstGeneral_Precision_Distribution82Analog 137 }
First_source_1_branch_38_output_voltage OBJECT-TYPE
	SYNTAX INTEGER
	UNITS     "0.01 "
	ACCESS read-only
	STATUS mandatory
	DESCRIPTION
		"First_source_1_branch_38_output_voltage"
	::= { FirstGeneral_Precision_Distribution82Analog 138 }
First_source_1_branch_39_output_voltage OBJECT-TYPE
	SYNTAX INTEGER
	UNITS     "0.01 "
	ACCESS read-only
	STATUS mandatory
	DESCRIPTION
		"First_source_1_branch_39_output_voltage"
	::= { FirstGeneral_Precision_Distribution82Analog 139 }
First_source_1_branch_40_output_voltage OBJECT-TYPE
	SYNTAX INTEGER
	UNITS     "0.01 "
	ACCESS read-only
	STATUS mandatory
	DESCRIPTION
		"First_source_1_branch_40_output_voltage"
	::= { FirstGeneral_Precision_Distribution82Analog 140 }
First_source_1_branch_41_output_voltage OBJECT-TYPE
	SYNTAX INTEGER
	UNITS     "0.01 "
	ACCESS read-only
	STATUS mandatory
	DESCRIPTION
		"First_source_1_branch_41_output_voltage"
	::= { FirstGeneral_Precision_Distribution82Analog 141 }
First_source_1_branch_42_output_voltage OBJECT-TYPE
	SYNTAX INTEGER
	UNITS     "0.01 "
	ACCESS read-only
	STATUS mandatory
	DESCRIPTION
		"First_source_1_branch_42_output_voltage"
	::= { FirstGeneral_Precision_Distribution82Analog 142 }
First_source_1_branch_43_output_voltage OBJECT-TYPE
	SYNTAX INTEGER
	UNITS     "0.01 "
	ACCESS read-only
	STATUS mandatory
	DESCRIPTION
		"First_source_1_branch_43_output_voltage"
	::= { FirstGeneral_Precision_Distribution82Analog 143 }
First_source_1_branch_44_output_voltage OBJECT-TYPE
	SYNTAX INTEGER
	UNITS     "0.01 "
	ACCESS read-only
	STATUS mandatory
	DESCRIPTION
		"First_source_1_branch_44_output_voltage"
	::= { FirstGeneral_Precision_Distribution82Analog 144 }
First_source_1_branch_45_output_voltage OBJECT-TYPE
	SYNTAX INTEGER
	UNITS     "0.01 "
	ACCESS read-only
	STATUS mandatory
	DESCRIPTION
		"First_source_1_branch_45_output_voltage"
	::= { FirstGeneral_Precision_Distribution82Analog 145 }
First_source_1_branch_46_output_voltage OBJECT-TYPE
	SYNTAX INTEGER
	UNITS     "0.01 "
	ACCESS read-only
	STATUS mandatory
	DESCRIPTION
		"First_source_1_branch_46_output_voltage"
	::= { FirstGeneral_Precision_Distribution82Analog 146 }
First_source_1_branch_47_output_voltage OBJECT-TYPE
	SYNTAX INTEGER
	UNITS     "0.01 "
	ACCESS read-only
	STATUS mandatory
	DESCRIPTION
		"First_source_1_branch_47_output_voltage"
	::= { FirstGeneral_Precision_Distribution82Analog 147 }
First_source_1_branch_48_output_voltage OBJECT-TYPE
	SYNTAX INTEGER
	UNITS     "0.01 "
	ACCESS read-only
	STATUS mandatory
	DESCRIPTION
		"First_source_1_branch_48_output_voltage"
	::= { FirstGeneral_Precision_Distribution82Analog 148 }
First_source_1_branch_49_output_voltage OBJECT-TYPE
	SYNTAX INTEGER
	UNITS     "0.01 "
	ACCESS read-only
	STATUS mandatory
	DESCRIPTION
		"First_source_1_branch_49_output_voltage"
	::= { FirstGeneral_Precision_Distribution82Analog 149 }
First_source_1_branch_50_output_voltage OBJECT-TYPE
	SYNTAX INTEGER
	UNITS     "0.01 "
	ACCESS read-only
	STATUS mandatory
	DESCRIPTION
		"First_source_1_branch_50_output_voltage"
	::= { FirstGeneral_Precision_Distribution82Analog 150 }
First_source_1_branch_51_output_voltage OBJECT-TYPE
	SYNTAX INTEGER
	UNITS     "0.01 "
	ACCESS read-only
	STATUS mandatory
	DESCRIPTION
		"First_source_1_branch_51_output_voltage"
	::= { FirstGeneral_Precision_Distribution82Analog 151 }
First_source_1_branch_52_output_voltage OBJECT-TYPE
	SYNTAX INTEGER
	UNITS     "0.01 "
	ACCESS read-only
	STATUS mandatory
	DESCRIPTION
		"First_source_1_branch_52_output_voltage"
	::= { FirstGeneral_Precision_Distribution82Analog 152 }
First_source_1_branch_53_output_voltage OBJECT-TYPE
	SYNTAX INTEGER
	UNITS     "0.01 "
	ACCESS read-only
	STATUS mandatory
	DESCRIPTION
		"First_source_1_branch_53_output_voltage"
	::= { FirstGeneral_Precision_Distribution82Analog 153 }
First_source_1_branch_54_output_voltage OBJECT-TYPE
	SYNTAX INTEGER
	UNITS     "0.01 "
	ACCESS read-only
	STATUS mandatory
	DESCRIPTION
		"First_source_1_branch_54_output_voltage"
	::= { FirstGeneral_Precision_Distribution82Analog 154 }
First_source_1_branch_55_output_voltage OBJECT-TYPE
	SYNTAX INTEGER
	UNITS     "0.01 "
	ACCESS read-only
	STATUS mandatory
	DESCRIPTION
		"First_source_1_branch_55_output_voltage"
	::= { FirstGeneral_Precision_Distribution82Analog 155 }
First_source_1_branch_56_output_voltage OBJECT-TYPE
	SYNTAX INTEGER
	UNITS     "0.01 "
	ACCESS read-only
	STATUS mandatory
	DESCRIPTION
		"First_source_1_branch_56_output_voltage"
	::= { FirstGeneral_Precision_Distribution82Analog 156 }
First_source_1_branch_57_output_voltage OBJECT-TYPE
	SYNTAX INTEGER
	UNITS     "0.01 "
	ACCESS read-only
	STATUS mandatory
	DESCRIPTION
		"First_source_1_branch_57_output_voltage"
	::= { FirstGeneral_Precision_Distribution82Analog 157 }
First_source_1_branch_58_output_voltage OBJECT-TYPE
	SYNTAX INTEGER
	UNITS     "0.01 "
	ACCESS read-only
	STATUS mandatory
	DESCRIPTION
		"First_source_1_branch_58_output_voltage"
	::= { FirstGeneral_Precision_Distribution82Analog 158 }
First_source_1_branch_59_output_voltage OBJECT-TYPE
	SYNTAX INTEGER
	UNITS     "0.01 "
	ACCESS read-only
	STATUS mandatory
	DESCRIPTION
		"First_source_1_branch_59_output_voltage"
	::= { FirstGeneral_Precision_Distribution82Analog 159 }
First_source_1_branch_60_output_voltage OBJECT-TYPE
	SYNTAX INTEGER
	UNITS     "0.01 "
	ACCESS read-only
	STATUS mandatory
	DESCRIPTION
		"First_source_1_branch_60_output_voltage"
	::= { FirstGeneral_Precision_Distribution82Analog 160 }
First_source_1_branch_61_output_voltage OBJECT-TYPE
	SYNTAX INTEGER
	UNITS     "0.01 "
	ACCESS read-only
	STATUS mandatory
	DESCRIPTION
		"First_source_1_branch_61_output_voltage"
	::= { FirstGeneral_Precision_Distribution82Analog 161 }
First_source_1_branch_62_output_voltage OBJECT-TYPE
	SYNTAX INTEGER
	UNITS     "0.01 "
	ACCESS read-only
	STATUS mandatory
	DESCRIPTION
		"First_source_1_branch_62_output_voltage"
	::= { FirstGeneral_Precision_Distribution82Analog 162 }
First_source_1_branch_63_output_voltage OBJECT-TYPE
	SYNTAX INTEGER
	UNITS     "0.01 "
	ACCESS read-only
	STATUS mandatory
	DESCRIPTION
		"First_source_1_branch_63_output_voltage"
	::= { FirstGeneral_Precision_Distribution82Analog 163 }
First_source_1_branch_64_output_voltage OBJECT-TYPE
	SYNTAX INTEGER
	UNITS     "0.01 "
	ACCESS read-only
	STATUS mandatory
	DESCRIPTION
		"First_source_1_branch_64_output_voltage"
	::= { FirstGeneral_Precision_Distribution82Analog 164 }
First_source_1_branch_65_output_voltage OBJECT-TYPE
	SYNTAX INTEGER
	UNITS     "0.01 "
	ACCESS read-only
	STATUS mandatory
	DESCRIPTION
		"First_source_1_branch_65_output_voltage"
	::= { FirstGeneral_Precision_Distribution82Analog 165 }
First_source_1_branch_66_output_voltage OBJECT-TYPE
	SYNTAX INTEGER
	UNITS     "0.01 "
	ACCESS read-only
	STATUS mandatory
	DESCRIPTION
		"First_source_1_branch_66_output_voltage"
	::= { FirstGeneral_Precision_Distribution82Analog 166 }
First_source_1_branch_67_output_voltage OBJECT-TYPE
	SYNTAX INTEGER
	UNITS     "0.01 "
	ACCESS read-only
	STATUS mandatory
	DESCRIPTION
		"First_source_1_branch_67_output_voltage"
	::= { FirstGeneral_Precision_Distribution82Analog 167 }
First_source_1_branch_68_output_voltage OBJECT-TYPE
	SYNTAX INTEGER
	UNITS     "0.01 "
	ACCESS read-only
	STATUS mandatory
	DESCRIPTION
		"First_source_1_branch_68_output_voltage"
	::= { FirstGeneral_Precision_Distribution82Analog 168 }
First_source_1_branch_69_output_voltage OBJECT-TYPE
	SYNTAX INTEGER
	UNITS     "0.01 "
	ACCESS read-only
	STATUS mandatory
	DESCRIPTION
		"First_source_1_branch_69_output_voltage"
	::= { FirstGeneral_Precision_Distribution82Analog 169 }
First_source_1_branch_70_output_voltage OBJECT-TYPE
	SYNTAX INTEGER
	UNITS     "0.01 "
	ACCESS read-only
	STATUS mandatory
	DESCRIPTION
		"First_source_1_branch_70_output_voltage"
	::= { FirstGeneral_Precision_Distribution82Analog 170 }
First_source_1_branch_71_output_voltage OBJECT-TYPE
	SYNTAX INTEGER
	UNITS     "0.01 "
	ACCESS read-only
	STATUS mandatory
	DESCRIPTION
		"First_source_1_branch_71_output_voltage"
	::= { FirstGeneral_Precision_Distribution82Analog 171 }
First_source_1_branch_72_output_voltage OBJECT-TYPE
	SYNTAX INTEGER
	UNITS     "0.01 "
	ACCESS read-only
	STATUS mandatory
	DESCRIPTION
		"First_source_1_branch_72_output_voltage"
	::= { FirstGeneral_Precision_Distribution82Analog 172 }
First_source_1_branch_73_output_voltage OBJECT-TYPE
	SYNTAX INTEGER
	UNITS     "0.01 "
	ACCESS read-only
	STATUS mandatory
	DESCRIPTION
		"First_source_1_branch_73_output_voltage"
	::= { FirstGeneral_Precision_Distribution82Analog 173 }
First_source_1_branch_74_output_voltage OBJECT-TYPE
	SYNTAX INTEGER
	UNITS     "0.01 "
	ACCESS read-only
	STATUS mandatory
	DESCRIPTION
		"First_source_1_branch_74_output_voltage"
	::= { FirstGeneral_Precision_Distribution82Analog 174 }
First_source_1_branch_75_output_voltage OBJECT-TYPE
	SYNTAX INTEGER
	UNITS     "0.01 "
	ACCESS read-only
	STATUS mandatory
	DESCRIPTION
		"First_source_1_branch_75_output_voltage"
	::= { FirstGeneral_Precision_Distribution82Analog 175 }
First_source_1_branch_76_output_voltage OBJECT-TYPE
	SYNTAX INTEGER
	UNITS     "0.01 "
	ACCESS read-only
	STATUS mandatory
	DESCRIPTION
		"First_source_1_branch_76_output_voltage"
	::= { FirstGeneral_Precision_Distribution82Analog 176 }
First_source_1_branch_77_output_voltage OBJECT-TYPE
	SYNTAX INTEGER
	UNITS     "0.01 "
	ACCESS read-only
	STATUS mandatory
	DESCRIPTION
		"First_source_1_branch_77_output_voltage"
	::= { FirstGeneral_Precision_Distribution82Analog 177 }
First_source_1_branch_78_output_voltage OBJECT-TYPE
	SYNTAX INTEGER
	UNITS     "0.01 "
	ACCESS read-only
	STATUS mandatory
	DESCRIPTION
		"First_source_1_branch_78_output_voltage"
	::= { FirstGeneral_Precision_Distribution82Analog 178 }
First_source_1_branch_79_output_voltage OBJECT-TYPE
	SYNTAX INTEGER
	UNITS     "0.01 "
	ACCESS read-only
	STATUS mandatory
	DESCRIPTION
		"First_source_1_branch_79_output_voltage"
	::= { FirstGeneral_Precision_Distribution82Analog 179 }
First_source_1_branch_80_output_voltage OBJECT-TYPE
	SYNTAX INTEGER
	UNITS     "0.01 "
	ACCESS read-only
	STATUS mandatory
	DESCRIPTION
		"First_source_1_branch_80_output_voltage"
	::= { FirstGeneral_Precision_Distribution82Analog 180 }
First_source_1_branch_81_output_voltage OBJECT-TYPE
	SYNTAX INTEGER
	UNITS     "0.01 "
	ACCESS read-only
	STATUS mandatory
	DESCRIPTION
		"First_source_1_branch_81_output_voltage"
	::= { FirstGeneral_Precision_Distribution82Analog 181 }
First_source_1_branch_82_output_voltage OBJECT-TYPE
	SYNTAX INTEGER
	UNITS     "0.01 "
	ACCESS read-only
	STATUS mandatory
	DESCRIPTION
		"First_source_1_branch_82_output_voltage"
	::= { FirstGeneral_Precision_Distribution82Analog 182 }
First_source_1_branch_83_output_voltage OBJECT-TYPE
	SYNTAX INTEGER
	UNITS     "0.01 "
	ACCESS read-only
	STATUS mandatory
	DESCRIPTION
		"First_source_1_branch_83_output_voltage"
	::= { FirstGeneral_Precision_Distribution82Analog 183 }
First_source_1_branch_84_output_voltage OBJECT-TYPE
	SYNTAX INTEGER
	UNITS     "0.01 "
	ACCESS read-only
	STATUS mandatory
	DESCRIPTION
		"First_source_1_branch_84_output_voltage"
	::= { FirstGeneral_Precision_Distribution82Analog 184 }
First_source_1_branch_85_output_voltage OBJECT-TYPE
	SYNTAX INTEGER
	UNITS     "0.01 "
	ACCESS read-only
	STATUS mandatory
	DESCRIPTION
		"First_source_1_branch_85_output_voltage"
	::= { FirstGeneral_Precision_Distribution82Analog 185 }
First_source_1_branch_86_output_voltage OBJECT-TYPE
	SYNTAX INTEGER
	UNITS     "0.01 "
	ACCESS read-only
	STATUS mandatory
	DESCRIPTION
		"First_source_1_branch_86_output_voltage"
	::= { FirstGeneral_Precision_Distribution82Analog 186 }
First_source_1_branch_87_output_voltage OBJECT-TYPE
	SYNTAX INTEGER
	UNITS     "0.01 "
	ACCESS read-only
	STATUS mandatory
	DESCRIPTION
		"First_source_1_branch_87_output_voltage"
	::= { FirstGeneral_Precision_Distribution82Analog 187 }
First_source_1_branch_88_output_voltage OBJECT-TYPE
	SYNTAX INTEGER
	UNITS     "0.01 "
	ACCESS read-only
	STATUS mandatory
	DESCRIPTION
		"First_source_1_branch_88_output_voltage"
	::= { FirstGeneral_Precision_Distribution82Analog 188 }
First_source_1_branch_89_output_voltage OBJECT-TYPE
	SYNTAX INTEGER
	UNITS     "0.01 "
	ACCESS read-only
	STATUS mandatory
	DESCRIPTION
		"First_source_1_branch_89_output_voltage"
	::= { FirstGeneral_Precision_Distribution82Analog 189 }
First_source_1_branch_90_output_voltage OBJECT-TYPE
	SYNTAX INTEGER
	UNITS     "0.01 "
	ACCESS read-only
	STATUS mandatory
	DESCRIPTION
		"First_source_1_branch_90_output_voltage"
	::= { FirstGeneral_Precision_Distribution82Analog 190 }
First_source_1_branch_91_output_voltage OBJECT-TYPE
	SYNTAX INTEGER
	UNITS     "0.01 "
	ACCESS read-only
	STATUS mandatory
	DESCRIPTION
		"First_source_1_branch_91_output_voltage"
	::= { FirstGeneral_Precision_Distribution82Analog 191 }
First_source_1_branch_92_output_voltage OBJECT-TYPE
	SYNTAX INTEGER
	UNITS     "0.01 "
	ACCESS read-only
	STATUS mandatory
	DESCRIPTION
		"First_source_1_branch_92_output_voltage"
	::= { FirstGeneral_Precision_Distribution82Analog 192 }
First_source_1_branch_93_output_voltage OBJECT-TYPE
	SYNTAX INTEGER
	UNITS     "0.01 "
	ACCESS read-only
	STATUS mandatory
	DESCRIPTION
		"First_source_1_branch_93_output_voltage"
	::= { FirstGeneral_Precision_Distribution82Analog 193 }
First_source_1_branch_94_output_voltage OBJECT-TYPE
	SYNTAX INTEGER
	UNITS     "0.01 "
	ACCESS read-only
	STATUS mandatory
	DESCRIPTION
		"First_source_1_branch_94_output_voltage"
	::= { FirstGeneral_Precision_Distribution82Analog 194 }
First_source_1_branch_95_output_voltage OBJECT-TYPE
	SYNTAX INTEGER
	UNITS     "0.01 "
	ACCESS read-only
	STATUS mandatory
	DESCRIPTION
		"First_source_1_branch_95_output_voltage"
	::= { FirstGeneral_Precision_Distribution82Analog 195 }
First_source_1_branch_96_output_voltage OBJECT-TYPE
	SYNTAX INTEGER
	UNITS     "0.01 "
	ACCESS read-only
	STATUS mandatory
	DESCRIPTION
		"First_source_1_branch_96_output_voltage"
	::= { FirstGeneral_Precision_Distribution82Analog 196 }
First_source_1_branch_97_output_voltage OBJECT-TYPE
	SYNTAX INTEGER
	UNITS     "0.01 "
	ACCESS read-only
	STATUS mandatory
	DESCRIPTION
		"First_source_1_branch_97_output_voltage"
	::= { FirstGeneral_Precision_Distribution82Analog 197 }
First_source_1_branch_98_output_voltage OBJECT-TYPE
	SYNTAX INTEGER
	UNITS     "0.01 "
	ACCESS read-only
	STATUS mandatory
	DESCRIPTION
		"First_source_1_branch_98_output_voltage"
	::= { FirstGeneral_Precision_Distribution82Analog 198 }
First_source_1_branch_99_output_voltage OBJECT-TYPE
	SYNTAX INTEGER
	UNITS     "0.01 "
	ACCESS read-only
	STATUS mandatory
	DESCRIPTION
		"First_source_1_branch_99_output_voltage"
	::= { FirstGeneral_Precision_Distribution82Analog 199 }
First_source_1_branch_100_output_voltage OBJECT-TYPE
	SYNTAX INTEGER
	UNITS     "0.01 "
	ACCESS read-only
	STATUS mandatory
	DESCRIPTION
		"First_source_1_branch_100_output_voltage"
	::= { FirstGeneral_Precision_Distribution82Analog 200 }
First_source_1_branch_1_output_Electric_Energy OBJECT-TYPE
	SYNTAX INTEGER
	UNITS     "0.01KWh "
	ACCESS read-only
	STATUS mandatory
	DESCRIPTION
		"First_source_1_branch_1_output_Electric_Energy"
	::= { FirstGeneral_Precision_Distribution82Analog 201 }
First_source_1_branch_2_output_Electric_Energy OBJECT-TYPE
	SYNTAX INTEGER
	UNITS     "0.01 "
	ACCESS read-only
	STATUS mandatory
	DESCRIPTION
		"First_source_1_branch_2_output_Electric_Energy"
	::= { FirstGeneral_Precision_Distribution82Analog 202 }
First_source_1_branch_3_output_Electric_Energy OBJECT-TYPE
	SYNTAX INTEGER
	UNITS     "0.01 "
	ACCESS read-only
	STATUS mandatory
	DESCRIPTION
		"First_source_1_branch_3_output_Electric_Energy"
	::= { FirstGeneral_Precision_Distribution82Analog 203 }
First_source_1_branch_4_output_Electric_Energy OBJECT-TYPE
	SYNTAX INTEGER
	UNITS     "0.01 "
	ACCESS read-only
	STATUS mandatory
	DESCRIPTION
		"First_source_1_branch_4_output_Electric_Energy"
	::= { FirstGeneral_Precision_Distribution82Analog 204 }
First_source_1_branch_5_output_Electric_Energy OBJECT-TYPE
	SYNTAX INTEGER
	UNITS     "0.01 "
	ACCESS read-only
	STATUS mandatory
	DESCRIPTION
		"First_source_1_branch_5_output_Electric_Energy"
	::= { FirstGeneral_Precision_Distribution82Analog 205 }
First_source_1_branch_6_output_Electric_Energy OBJECT-TYPE
	SYNTAX INTEGER
	UNITS     "0.01 "
	ACCESS read-only
	STATUS mandatory
	DESCRIPTION
		"First_source_1_branch_6_output_Electric_Energy"
	::= { FirstGeneral_Precision_Distribution82Analog 206 }
First_source_1_branch_7_output_Electric_Energy OBJECT-TYPE
	SYNTAX INTEGER
	UNITS     "0.01 "
	ACCESS read-only
	STATUS mandatory
	DESCRIPTION
		"First_source_1_branch_7_output_Electric_Energy"
	::= { FirstGeneral_Precision_Distribution82Analog 207 }
First_source_1_branch_8_output_Electric_Energy OBJECT-TYPE
	SYNTAX INTEGER
	UNITS     "0.01 "
	ACCESS read-only
	STATUS mandatory
	DESCRIPTION
		"First_source_1_branch_8_output_Electric_Energy"
	::= { FirstGeneral_Precision_Distribution82Analog 208 }
First_source_1_branch_9_output_Electric_Energy OBJECT-TYPE
	SYNTAX INTEGER
	UNITS     "0.01 "
	ACCESS read-only
	STATUS mandatory
	DESCRIPTION
		"First_source_1_branch_9_output_Electric_Energy"
	::= { FirstGeneral_Precision_Distribution82Analog 209 }
First_source_1_branch_10_output_Electric_Energy OBJECT-TYPE
	SYNTAX INTEGER
	UNITS     "0.01 "
	ACCESS read-only
	STATUS mandatory
	DESCRIPTION
		"First_source_1_branch_10_output_Electric_Energy"
	::= { FirstGeneral_Precision_Distribution82Analog 210 }
First_source_1_branch_11_output_Electric_Energy OBJECT-TYPE
	SYNTAX INTEGER
	UNITS     "0.01 "
	ACCESS read-only
	STATUS mandatory
	DESCRIPTION
		"First_source_1_branch_11_output_Electric_Energy"
	::= { FirstGeneral_Precision_Distribution82Analog 211 }
First_source_1_branch_12_output_Electric_Energy OBJECT-TYPE
	SYNTAX INTEGER
	UNITS     "0.01 "
	ACCESS read-only
	STATUS mandatory
	DESCRIPTION
		"First_source_1_branch_12_output_Electric_Energy"
	::= { FirstGeneral_Precision_Distribution82Analog 212 }
First_source_1_branch_13_output_Electric_Energy OBJECT-TYPE
	SYNTAX INTEGER
	UNITS     "0.01 "
	ACCESS read-only
	STATUS mandatory
	DESCRIPTION
		"First_source_1_branch_13_output_Electric_Energy"
	::= { FirstGeneral_Precision_Distribution82Analog 213 }
First_source_1_branch_14_output_Electric_Energy OBJECT-TYPE
	SYNTAX INTEGER
	UNITS     "0.01 "
	ACCESS read-only
	STATUS mandatory
	DESCRIPTION
		"First_source_1_branch_14_output_Electric_Energy"
	::= { FirstGeneral_Precision_Distribution82Analog 214 }
First_source_1_branch_15_output_Electric_Energy OBJECT-TYPE
	SYNTAX INTEGER
	UNITS     "0.01 "
	ACCESS read-only
	STATUS mandatory
	DESCRIPTION
		"First_source_1_branch_15_output_Electric_Energy"
	::= { FirstGeneral_Precision_Distribution82Analog 215 }
First_source_1_branch_16_output_Electric_Energy OBJECT-TYPE
	SYNTAX INTEGER
	UNITS     "0.01 "
	ACCESS read-only
	STATUS mandatory
	DESCRIPTION
		"First_source_1_branch_16_output_Electric_Energy"
	::= { FirstGeneral_Precision_Distribution82Analog 216 }
First_source_1_branch_17_output_Electric_Energy OBJECT-TYPE
	SYNTAX INTEGER
	UNITS     "0.01 "
	ACCESS read-only
	STATUS mandatory
	DESCRIPTION
		"First_source_1_branch_17_output_Electric_Energy"
	::= { FirstGeneral_Precision_Distribution82Analog 217 }
First_source_1_branch_18_output_Electric_Energy OBJECT-TYPE
	SYNTAX INTEGER
	UNITS     "0.01 "
	ACCESS read-only
	STATUS mandatory
	DESCRIPTION
		"First_source_1_branch_18_output_Electric_Energy"
	::= { FirstGeneral_Precision_Distribution82Analog 218 }
First_source_1_branch_19_output_Electric_Energy OBJECT-TYPE
	SYNTAX INTEGER
	UNITS     "0.01 "
	ACCESS read-only
	STATUS mandatory
	DESCRIPTION
		"First_source_1_branch_19_output_Electric_Energy"
	::= { FirstGeneral_Precision_Distribution82Analog 219 }
First_source_1_branch_20_output_Electric_Energy OBJECT-TYPE
	SYNTAX INTEGER
	UNITS     "0.01 "
	ACCESS read-only
	STATUS mandatory
	DESCRIPTION
		"First_source_1_branch_20_output_Electric_Energy"
	::= { FirstGeneral_Precision_Distribution82Analog 220 }
First_source_1_branch_21_output_Electric_Energy OBJECT-TYPE
	SYNTAX INTEGER
	UNITS     "0.01 "
	ACCESS read-only
	STATUS mandatory
	DESCRIPTION
		"First_source_1_branch_21_output_Electric_Energy"
	::= { FirstGeneral_Precision_Distribution82Analog 221 }
First_source_1_branch_22_output_Electric_Energy OBJECT-TYPE
	SYNTAX INTEGER
	UNITS     "0.01 "
	ACCESS read-only
	STATUS mandatory
	DESCRIPTION
		"First_source_1_branch_22_output_Electric_Energy"
	::= { FirstGeneral_Precision_Distribution82Analog 222 }
First_source_1_branch_23_output_Electric_Energy OBJECT-TYPE
	SYNTAX INTEGER
	UNITS     "0.01 "
	ACCESS read-only
	STATUS mandatory
	DESCRIPTION
		"First_source_1_branch_23_output_Electric_Energy"
	::= { FirstGeneral_Precision_Distribution82Analog 223 }
First_source_1_branch_24_output_Electric_Energy OBJECT-TYPE
	SYNTAX INTEGER
	UNITS     "0.01 "
	ACCESS read-only
	STATUS mandatory
	DESCRIPTION
		"First_source_1_branch_24_output_Electric_Energy"
	::= { FirstGeneral_Precision_Distribution82Analog 224 }
First_source_1_branch_25_output_Electric_Energy OBJECT-TYPE
	SYNTAX INTEGER
	UNITS     "0.01 "
	ACCESS read-only
	STATUS mandatory
	DESCRIPTION
		"First_source_1_branch_25_output_Electric_Energy"
	::= { FirstGeneral_Precision_Distribution82Analog 225 }
First_source_1_branch_26_output_Electric_Energy OBJECT-TYPE
	SYNTAX INTEGER
	UNITS     "0.01 "
	ACCESS read-only
	STATUS mandatory
	DESCRIPTION
		"First_source_1_branch_26_output_Electric_Energy"
	::= { FirstGeneral_Precision_Distribution82Analog 226 }
First_source_1_branch_27_output_Electric_Energy OBJECT-TYPE
	SYNTAX INTEGER
	UNITS     "0.01 "
	ACCESS read-only
	STATUS mandatory
	DESCRIPTION
		"First_source_1_branch_27_output_Electric_Energy"
	::= { FirstGeneral_Precision_Distribution82Analog 227 }
First_source_1_branch_28_output_Electric_Energy OBJECT-TYPE
	SYNTAX INTEGER
	UNITS     "0.01 "
	ACCESS read-only
	STATUS mandatory
	DESCRIPTION
		"First_source_1_branch_28_output_Electric_Energy"
	::= { FirstGeneral_Precision_Distribution82Analog 228 }
First_source_1_branch_29_output_Electric_Energy OBJECT-TYPE
	SYNTAX INTEGER
	UNITS     "0.01 "
	ACCESS read-only
	STATUS mandatory
	DESCRIPTION
		"First_source_1_branch_29_output_Electric_Energy"
	::= { FirstGeneral_Precision_Distribution82Analog 229 }
First_source_1_branch_30_output_Electric_Energy OBJECT-TYPE
	SYNTAX INTEGER
	UNITS     "0.01 "
	ACCESS read-only
	STATUS mandatory
	DESCRIPTION
		"First_source_1_branch_30_output_Electric_Energy"
	::= { FirstGeneral_Precision_Distribution82Analog 230 }
First_source_1_branch_31_output_Electric_Energy OBJECT-TYPE
	SYNTAX INTEGER
	UNITS     "0.01 "
	ACCESS read-only
	STATUS mandatory
	DESCRIPTION
		"First_source_1_branch_31_output_Electric_Energy"
	::= { FirstGeneral_Precision_Distribution82Analog 231 }
First_source_1_branch_32_output_Electric_Energy OBJECT-TYPE
	SYNTAX INTEGER
	UNITS     "0.01 "
	ACCESS read-only
	STATUS mandatory
	DESCRIPTION
		"First_source_1_branch_32_output_Electric_Energy"
	::= { FirstGeneral_Precision_Distribution82Analog 232 }
First_source_1_branch_33_output_Electric_Energy OBJECT-TYPE
	SYNTAX INTEGER
	UNITS     "0.01 "
	ACCESS read-only
	STATUS mandatory
	DESCRIPTION
		"First_source_1_branch_33_output_Electric_Energy"
	::= { FirstGeneral_Precision_Distribution82Analog 233 }
First_source_1_branch_34_output_Electric_Energy OBJECT-TYPE
	SYNTAX INTEGER
	UNITS     "0.01 "
	ACCESS read-only
	STATUS mandatory
	DESCRIPTION
		"First_source_1_branch_34_output_Electric_Energy"
	::= { FirstGeneral_Precision_Distribution82Analog 234 }
First_source_1_branch_35_output_Electric_Energy OBJECT-TYPE
	SYNTAX INTEGER
	UNITS     "0.01 "
	ACCESS read-only
	STATUS mandatory
	DESCRIPTION
		"First_source_1_branch_35_output_Electric_Energy"
	::= { FirstGeneral_Precision_Distribution82Analog 235 }
First_source_1_branch_36_output_Electric_Energy OBJECT-TYPE
	SYNTAX INTEGER
	UNITS     "0.01 "
	ACCESS read-only
	STATUS mandatory
	DESCRIPTION
		"First_source_1_branch_36_output_Electric_Energy"
	::= { FirstGeneral_Precision_Distribution82Analog 236 }
First_source_1_branch_37_output_Electric_Energy OBJECT-TYPE
	SYNTAX INTEGER
	UNITS     "0.01 "
	ACCESS read-only
	STATUS mandatory
	DESCRIPTION
		"First_source_1_branch_37_output_Electric_Energy"
	::= { FirstGeneral_Precision_Distribution82Analog 237 }
First_source_1_branch_38_output_Electric_Energy OBJECT-TYPE
	SYNTAX INTEGER
	UNITS     "0.01 "
	ACCESS read-only
	STATUS mandatory
	DESCRIPTION
		"First_source_1_branch_38_output_Electric_Energy"
	::= { FirstGeneral_Precision_Distribution82Analog 238 }
First_source_1_branch_39_output_Electric_Energy OBJECT-TYPE
	SYNTAX INTEGER
	UNITS     "0.01 "
	ACCESS read-only
	STATUS mandatory
	DESCRIPTION
		"First_source_1_branch_39_output_Electric_Energy"
	::= { FirstGeneral_Precision_Distribution82Analog 239 }
First_source_1_branch_40_output_Electric_Energy OBJECT-TYPE
	SYNTAX INTEGER
	UNITS     "0.01 "
	ACCESS read-only
	STATUS mandatory
	DESCRIPTION
		"First_source_1_branch_40_output_Electric_Energy"
	::= { FirstGeneral_Precision_Distribution82Analog 240 }
First_source_1_branch_41_output_Electric_Energy OBJECT-TYPE
	SYNTAX INTEGER
	UNITS     "0.01 "
	ACCESS read-only
	STATUS mandatory
	DESCRIPTION
		"First_source_1_branch_41_output_Electric_Energy"
	::= { FirstGeneral_Precision_Distribution82Analog 241 }
First_source_1_branch_42_output_Electric_Energy OBJECT-TYPE
	SYNTAX INTEGER
	UNITS     "0.01 "
	ACCESS read-only
	STATUS mandatory
	DESCRIPTION
		"First_source_1_branch_42_output_Electric_Energy"
	::= { FirstGeneral_Precision_Distribution82Analog 242 }
First_source_1_branch_43_output_Electric_Energy OBJECT-TYPE
	SYNTAX INTEGER
	UNITS     "0.01 "
	ACCESS read-only
	STATUS mandatory
	DESCRIPTION
		"First_source_1_branch_43_output_Electric_Energy"
	::= { FirstGeneral_Precision_Distribution82Analog 243 }
First_source_1_branch_44_output_Electric_Energy OBJECT-TYPE
	SYNTAX INTEGER
	UNITS     "0.01 "
	ACCESS read-only
	STATUS mandatory
	DESCRIPTION
		"First_source_1_branch_44_output_Electric_Energy"
	::= { FirstGeneral_Precision_Distribution82Analog 244 }
First_source_1_branch_45_output_Electric_Energy OBJECT-TYPE
	SYNTAX INTEGER
	UNITS     "0.01 "
	ACCESS read-only
	STATUS mandatory
	DESCRIPTION
		"First_source_1_branch_45_output_Electric_Energy"
	::= { FirstGeneral_Precision_Distribution82Analog 245 }
First_source_1_branch_46_output_Electric_Energy OBJECT-TYPE
	SYNTAX INTEGER
	UNITS     "0.01 "
	ACCESS read-only
	STATUS mandatory
	DESCRIPTION
		"First_source_1_branch_46_output_Electric_Energy"
	::= { FirstGeneral_Precision_Distribution82Analog 246 }
First_source_1_branch_47_output_Electric_Energy OBJECT-TYPE
	SYNTAX INTEGER
	UNITS     "0.01 "
	ACCESS read-only
	STATUS mandatory
	DESCRIPTION
		"First_source_1_branch_47_output_Electric_Energy"
	::= { FirstGeneral_Precision_Distribution82Analog 247 }
First_source_1_branch_48_output_Electric_Energy OBJECT-TYPE
	SYNTAX INTEGER
	UNITS     "0.01 "
	ACCESS read-only
	STATUS mandatory
	DESCRIPTION
		"First_source_1_branch_48_output_Electric_Energy"
	::= { FirstGeneral_Precision_Distribution82Analog 248 }
First_source_1_branch_49_output_Electric_Energy OBJECT-TYPE
	SYNTAX INTEGER
	UNITS     "0.01 "
	ACCESS read-only
	STATUS mandatory
	DESCRIPTION
		"First_source_1_branch_49_output_Electric_Energy"
	::= { FirstGeneral_Precision_Distribution82Analog 249 }
First_source_1_branch_50_output_Electric_Energy OBJECT-TYPE
	SYNTAX INTEGER
	UNITS     "0.01 "
	ACCESS read-only
	STATUS mandatory
	DESCRIPTION
		"First_source_1_branch_50_output_Electric_Energy"
	::= { FirstGeneral_Precision_Distribution82Analog 250 }
First_source_1_branch_51_output_Electric_Energy OBJECT-TYPE
	SYNTAX INTEGER
	UNITS     "0.01 "
	ACCESS read-only
	STATUS mandatory
	DESCRIPTION
		"First_source_1_branch_51_output_Electric_Energy"
	::= { FirstGeneral_Precision_Distribution82Analog 251 }
First_source_1_branch_52_output_Electric_Energy OBJECT-TYPE
	SYNTAX INTEGER
	UNITS     "0.01 "
	ACCESS read-only
	STATUS mandatory
	DESCRIPTION
		"First_source_1_branch_52_output_Electric_Energy"
	::= { FirstGeneral_Precision_Distribution82Analog 252 }
First_source_1_branch_53_output_Electric_Energy OBJECT-TYPE
	SYNTAX INTEGER
	UNITS     "0.01 "
	ACCESS read-only
	STATUS mandatory
	DESCRIPTION
		"First_source_1_branch_53_output_Electric_Energy"
	::= { FirstGeneral_Precision_Distribution82Analog 253 }
First_source_1_branch_54_output_Electric_Energy OBJECT-TYPE
	SYNTAX INTEGER
	UNITS     "0.01 "
	ACCESS read-only
	STATUS mandatory
	DESCRIPTION
		"First_source_1_branch_54_output_Electric_Energy"
	::= { FirstGeneral_Precision_Distribution82Analog 254 }
First_source_1_branch_55_output_Electric_Energy OBJECT-TYPE
	SYNTAX INTEGER
	UNITS     "0.01 "
	ACCESS read-only
	STATUS mandatory
	DESCRIPTION
		"First_source_1_branch_55_output_Electric_Energy"
	::= { FirstGeneral_Precision_Distribution82Analog 255 }
First_source_1_branch_56_output_Electric_Energy OBJECT-TYPE
	SYNTAX INTEGER
	UNITS     "0.01 "
	ACCESS read-only
	STATUS mandatory
	DESCRIPTION
		"First_source_1_branch_56_output_Electric_Energy"
	::= { FirstGeneral_Precision_Distribution82Analog 256 }
First_source_1_branch_57_output_Electric_Energy OBJECT-TYPE
	SYNTAX INTEGER
	UNITS     "0.01 "
	ACCESS read-only
	STATUS mandatory
	DESCRIPTION
		"First_source_1_branch_57_output_Electric_Energy"
	::= { FirstGeneral_Precision_Distribution82Analog 257 }
First_source_1_branch_58_output_Electric_Energy OBJECT-TYPE
	SYNTAX INTEGER
	UNITS     "0.01 "
	ACCESS read-only
	STATUS mandatory
	DESCRIPTION
		"First_source_1_branch_58_output_Electric_Energy"
	::= { FirstGeneral_Precision_Distribution82Analog 258 }
First_source_1_branch_59_output_Electric_Energy OBJECT-TYPE
	SYNTAX INTEGER
	UNITS     "0.01 "
	ACCESS read-only
	STATUS mandatory
	DESCRIPTION
		"First_source_1_branch_59_output_Electric_Energy"
	::= { FirstGeneral_Precision_Distribution82Analog 259 }
First_source_1_branch_60_output_Electric_Energy OBJECT-TYPE
	SYNTAX INTEGER
	UNITS     "0.01 "
	ACCESS read-only
	STATUS mandatory
	DESCRIPTION
		"First_source_1_branch_60_output_Electric_Energy"
	::= { FirstGeneral_Precision_Distribution82Analog 260 }
First_source_1_branch_61_output_Electric_Energy OBJECT-TYPE
	SYNTAX INTEGER
	UNITS     "0.01 "
	ACCESS read-only
	STATUS mandatory
	DESCRIPTION
		"First_source_1_branch_61_output_Electric_Energy"
	::= { FirstGeneral_Precision_Distribution82Analog 261 }
First_source_1_branch_62_output_Electric_Energy OBJECT-TYPE
	SYNTAX INTEGER
	UNITS     "0.01 "
	ACCESS read-only
	STATUS mandatory
	DESCRIPTION
		"First_source_1_branch_62_output_Electric_Energy"
	::= { FirstGeneral_Precision_Distribution82Analog 262 }
First_source_1_branch_63_output_Electric_Energy OBJECT-TYPE
	SYNTAX INTEGER
	UNITS     "0.01 "
	ACCESS read-only
	STATUS mandatory
	DESCRIPTION
		"First_source_1_branch_63_output_Electric_Energy"
	::= { FirstGeneral_Precision_Distribution82Analog 263 }
First_source_1_branch_64_output_Electric_Energy OBJECT-TYPE
	SYNTAX INTEGER
	UNITS     "0.01 "
	ACCESS read-only
	STATUS mandatory
	DESCRIPTION
		"First_source_1_branch_64_output_Electric_Energy"
	::= { FirstGeneral_Precision_Distribution82Analog 264 }
First_source_1_branch_65_output_Electric_Energy OBJECT-TYPE
	SYNTAX INTEGER
	UNITS     "0.01 "
	ACCESS read-only
	STATUS mandatory
	DESCRIPTION
		"First_source_1_branch_65_output_Electric_Energy"
	::= { FirstGeneral_Precision_Distribution82Analog 265 }
First_source_1_branch_66_output_Electric_Energy OBJECT-TYPE
	SYNTAX INTEGER
	UNITS     "0.01 "
	ACCESS read-only
	STATUS mandatory
	DESCRIPTION
		"First_source_1_branch_66_output_Electric_Energy"
	::= { FirstGeneral_Precision_Distribution82Analog 266 }
First_source_1_branch_67_output_Electric_Energy OBJECT-TYPE
	SYNTAX INTEGER
	UNITS     "0.01 "
	ACCESS read-only
	STATUS mandatory
	DESCRIPTION
		"First_source_1_branch_67_output_Electric_Energy"
	::= { FirstGeneral_Precision_Distribution82Analog 267 }
First_source_1_branch_68_output_Electric_Energy OBJECT-TYPE
	SYNTAX INTEGER
	UNITS     "0.01 "
	ACCESS read-only
	STATUS mandatory
	DESCRIPTION
		"First_source_1_branch_68_output_Electric_Energy"
	::= { FirstGeneral_Precision_Distribution82Analog 268 }
First_source_1_branch_69_output_Electric_Energy OBJECT-TYPE
	SYNTAX INTEGER
	UNITS     "0.01 "
	ACCESS read-only
	STATUS mandatory
	DESCRIPTION
		"First_source_1_branch_69_output_Electric_Energy"
	::= { FirstGeneral_Precision_Distribution82Analog 269 }
First_source_1_branch_70_output_Electric_Energy OBJECT-TYPE
	SYNTAX INTEGER
	UNITS     "0.01 "
	ACCESS read-only
	STATUS mandatory
	DESCRIPTION
		"First_source_1_branch_70_output_Electric_Energy"
	::= { FirstGeneral_Precision_Distribution82Analog 270 }
First_source_1_branch_71_output_Electric_Energy OBJECT-TYPE
	SYNTAX INTEGER
	UNITS     "0.01 "
	ACCESS read-only
	STATUS mandatory
	DESCRIPTION
		"First_source_1_branch_71_output_Electric_Energy"
	::= { FirstGeneral_Precision_Distribution82Analog 271 }
First_source_1_branch_72_output_Electric_Energy OBJECT-TYPE
	SYNTAX INTEGER
	UNITS     "0.01 "
	ACCESS read-only
	STATUS mandatory
	DESCRIPTION
		"First_source_1_branch_72_output_Electric_Energy"
	::= { FirstGeneral_Precision_Distribution82Analog 272 }
First_source_1_branch_73_output_Electric_Energy OBJECT-TYPE
	SYNTAX INTEGER
	UNITS     "0.01 "
	ACCESS read-only
	STATUS mandatory
	DESCRIPTION
		"First_source_1_branch_73_output_Electric_Energy"
	::= { FirstGeneral_Precision_Distribution82Analog 273 }
First_source_1_branch_74_output_Electric_Energy OBJECT-TYPE
	SYNTAX INTEGER
	UNITS     "0.01 "
	ACCESS read-only
	STATUS mandatory
	DESCRIPTION
		"First_source_1_branch_74_output_Electric_Energy"
	::= { FirstGeneral_Precision_Distribution82Analog 274 }
First_source_1_branch_75_output_Electric_Energy OBJECT-TYPE
	SYNTAX INTEGER
	UNITS     "0.01 "
	ACCESS read-only
	STATUS mandatory
	DESCRIPTION
		"First_source_1_branch_75_output_Electric_Energy"
	::= { FirstGeneral_Precision_Distribution82Analog 275 }
First_source_1_branch_76_output_Electric_Energy OBJECT-TYPE
	SYNTAX INTEGER
	UNITS     "0.01 "
	ACCESS read-only
	STATUS mandatory
	DESCRIPTION
		"First_source_1_branch_76_output_Electric_Energy"
	::= { FirstGeneral_Precision_Distribution82Analog 276 }
First_source_1_branch_77_output_Electric_Energy OBJECT-TYPE
	SYNTAX INTEGER
	UNITS     "0.01 "
	ACCESS read-only
	STATUS mandatory
	DESCRIPTION
		"First_source_1_branch_77_output_Electric_Energy"
	::= { FirstGeneral_Precision_Distribution82Analog 277 }
First_source_1_branch_78_output_Electric_Energy OBJECT-TYPE
	SYNTAX INTEGER
	UNITS     "0.01 "
	ACCESS read-only
	STATUS mandatory
	DESCRIPTION
		"First_source_1_branch_78_output_Electric_Energy"
	::= { FirstGeneral_Precision_Distribution82Analog 278 }
First_source_1_branch_79_output_Electric_Energy OBJECT-TYPE
	SYNTAX INTEGER
	UNITS     "0.01 "
	ACCESS read-only
	STATUS mandatory
	DESCRIPTION
		"First_source_1_branch_79_output_Electric_Energy"
	::= { FirstGeneral_Precision_Distribution82Analog 279 }
First_source_1_branch_80_output_Electric_Energy OBJECT-TYPE
	SYNTAX INTEGER
	UNITS     "0.01 "
	ACCESS read-only
	STATUS mandatory
	DESCRIPTION
		"First_source_1_branch_80_output_Electric_Energy"
	::= { FirstGeneral_Precision_Distribution82Analog 280 }
First_source_1_branch_81_output_Electric_Energy OBJECT-TYPE
	SYNTAX INTEGER
	UNITS     "0.01 "
	ACCESS read-only
	STATUS mandatory
	DESCRIPTION
		"First_source_1_branch_81_output_Electric_Energy"
	::= { FirstGeneral_Precision_Distribution82Analog 281 }
First_source_1_branch_82_output_Electric_Energy OBJECT-TYPE
	SYNTAX INTEGER
	UNITS     "0.01 "
	ACCESS read-only
	STATUS mandatory
	DESCRIPTION
		"First_source_1_branch_82_output_Electric_Energy"
	::= { FirstGeneral_Precision_Distribution82Analog 282 }
First_source_1_branch_83_output_Electric_Energy OBJECT-TYPE
	SYNTAX INTEGER
	UNITS     "0.01 "
	ACCESS read-only
	STATUS mandatory
	DESCRIPTION
		"First_source_1_branch_83_output_Electric_Energy"
	::= { FirstGeneral_Precision_Distribution82Analog 283 }
First_source_1_branch_84_output_Electric_Energy OBJECT-TYPE
	SYNTAX INTEGER
	UNITS     "0.01 "
	ACCESS read-only
	STATUS mandatory
	DESCRIPTION
		"First_source_1_branch_84_output_Electric_Energy"
	::= { FirstGeneral_Precision_Distribution82Analog 284 }
First_source_1_branch_85_output_Electric_Energy OBJECT-TYPE
	SYNTAX INTEGER
	UNITS     "0.01 "
	ACCESS read-only
	STATUS mandatory
	DESCRIPTION
		"First_source_1_branch_85_output_Electric_Energy"
	::= { FirstGeneral_Precision_Distribution82Analog 285 }
First_source_1_branch_86_output_Electric_Energy OBJECT-TYPE
	SYNTAX INTEGER
	UNITS     "0.01 "
	ACCESS read-only
	STATUS mandatory
	DESCRIPTION
		"First_source_1_branch_86_output_Electric_Energy"
	::= { FirstGeneral_Precision_Distribution82Analog 286 }
First_source_1_branch_87_output_Electric_Energy OBJECT-TYPE
	SYNTAX INTEGER
	UNITS     "0.01 "
	ACCESS read-only
	STATUS mandatory
	DESCRIPTION
		"First_source_1_branch_87_output_Electric_Energy"
	::= { FirstGeneral_Precision_Distribution82Analog 287 }
First_source_1_branch_88_output_Electric_Energy OBJECT-TYPE
	SYNTAX INTEGER
	UNITS     "0.01 "
	ACCESS read-only
	STATUS mandatory
	DESCRIPTION
		"First_source_1_branch_88_output_Electric_Energy"
	::= { FirstGeneral_Precision_Distribution82Analog 288 }
First_source_1_branch_89_output_Electric_Energy OBJECT-TYPE
	SYNTAX INTEGER
	UNITS     "0.01 "
	ACCESS read-only
	STATUS mandatory
	DESCRIPTION
		"First_source_1_branch_89_output_Electric_Energy"
	::= { FirstGeneral_Precision_Distribution82Analog 289 }
First_source_1_branch_90_output_Electric_Energy OBJECT-TYPE
	SYNTAX INTEGER
	UNITS     "0.01 "
	ACCESS read-only
	STATUS mandatory
	DESCRIPTION
		"First_source_1_branch_90_output_Electric_Energy"
	::= { FirstGeneral_Precision_Distribution82Analog 290 }
First_source_1_branch_91_output_Electric_Energy OBJECT-TYPE
	SYNTAX INTEGER
	UNITS     "0.01 "
	ACCESS read-only
	STATUS mandatory
	DESCRIPTION
		"First_source_1_branch_91_output_Electric_Energy"
	::= { FirstGeneral_Precision_Distribution82Analog 291 }
First_source_1_branch_92_output_Electric_Energy OBJECT-TYPE
	SYNTAX INTEGER
	UNITS     "0.01 "
	ACCESS read-only
	STATUS mandatory
	DESCRIPTION
		"First_source_1_branch_92_output_Electric_Energy"
	::= { FirstGeneral_Precision_Distribution82Analog 292 }
First_source_1_branch_93_output_Electric_Energy OBJECT-TYPE
	SYNTAX INTEGER
	UNITS     "0.01 "
	ACCESS read-only
	STATUS mandatory
	DESCRIPTION
		"First_source_1_branch_93_output_Electric_Energy"
	::= { FirstGeneral_Precision_Distribution82Analog 293 }
First_source_1_branch_94_output_Electric_Energy OBJECT-TYPE
	SYNTAX INTEGER
	UNITS     "0.01 "
	ACCESS read-only
	STATUS mandatory
	DESCRIPTION
		"First_source_1_branch_94_output_Electric_Energy"
	::= { FirstGeneral_Precision_Distribution82Analog 294 }
First_source_1_branch_95_output_Electric_Energy OBJECT-TYPE
	SYNTAX INTEGER
	UNITS     "0.01 "
	ACCESS read-only
	STATUS mandatory
	DESCRIPTION
		"First_source_1_branch_95_output_Electric_Energy"
	::= { FirstGeneral_Precision_Distribution82Analog 295 }
First_source_1_branch_96_output_Electric_Energy OBJECT-TYPE
	SYNTAX INTEGER
	UNITS     "0.01 "
	ACCESS read-only
	STATUS mandatory
	DESCRIPTION
		"First_source_1_branch_96_output_Electric_Energy"
	::= { FirstGeneral_Precision_Distribution82Analog 296 }
First_source_1_branch_97_output_Electric_Energy OBJECT-TYPE
	SYNTAX INTEGER
	UNITS     "0.01 "
	ACCESS read-only
	STATUS mandatory
	DESCRIPTION
		"First_source_1_branch_97_output_Electric_Energy"
	::= { FirstGeneral_Precision_Distribution82Analog 297 }
First_source_1_branch_98_output_Electric_Energy OBJECT-TYPE
	SYNTAX INTEGER
	UNITS     "0.01 "
	ACCESS read-only
	STATUS mandatory
	DESCRIPTION
		"First_source_1_branch_98_output_Electric_Energy"
	::= { FirstGeneral_Precision_Distribution82Analog 298 }
First_source_1_branch_99_output_Electric_Energy OBJECT-TYPE
	SYNTAX INTEGER
	UNITS     "0.01 "
	ACCESS read-only
	STATUS mandatory
	DESCRIPTION
		"First_source_1_branch_99_output_Electric_Energy"
	::= { FirstGeneral_Precision_Distribution82Analog 299 }
First_source_1_branch_100_output_Electric_Energy OBJECT-TYPE
	SYNTAX INTEGER
	UNITS     "0.01 "
	ACCESS read-only
	STATUS mandatory
	DESCRIPTION
		"First_source_1_branch_100_output_Electric_Energy"
	::= { FirstGeneral_Precision_Distribution82Analog 300 }
First_source_1_branch_1_output_current OBJECT-TYPE
	SYNTAX INTEGER
	UNITS     "0.01A "
	ACCESS read-only
	STATUS mandatory
	DESCRIPTION
		"First_source_1_branch_1_output_current"
	::= { FirstGeneral_Precision_Distribution82Analog 301 }
First_source_1_branch_2_output_current OBJECT-TYPE
	SYNTAX INTEGER
	UNITS     "0.01 "
	ACCESS read-only
	STATUS mandatory
	DESCRIPTION
		"First_source_1_branch_2_output_current"
	::= { FirstGeneral_Precision_Distribution82Analog 302 }
First_source_1_branch_3_output_current OBJECT-TYPE
	SYNTAX INTEGER
	UNITS     "0.01 "
	ACCESS read-only
	STATUS mandatory
	DESCRIPTION
		"First_source_1_branch_3_output_current"
	::= { FirstGeneral_Precision_Distribution82Analog 303 }
First_source_1_branch_4_output_current OBJECT-TYPE
	SYNTAX INTEGER
	UNITS     "0.01 "
	ACCESS read-only
	STATUS mandatory
	DESCRIPTION
		"First_source_1_branch_4_output_current"
	::= { FirstGeneral_Precision_Distribution82Analog 304 }
First_source_1_branch_5_output_current OBJECT-TYPE
	SYNTAX INTEGER
	UNITS     "0.01 "
	ACCESS read-only
	STATUS mandatory
	DESCRIPTION
		"First_source_1_branch_5_output_current"
	::= { FirstGeneral_Precision_Distribution82Analog 305 }
First_source_1_branch_6_output_current OBJECT-TYPE
	SYNTAX INTEGER
	UNITS     "0.01 "
	ACCESS read-only
	STATUS mandatory
	DESCRIPTION
		"First_source_1_branch_6_output_current"
	::= { FirstGeneral_Precision_Distribution82Analog 306 }
First_source_1_branch_7_output_current OBJECT-TYPE
	SYNTAX INTEGER
	UNITS     "0.01 "
	ACCESS read-only
	STATUS mandatory
	DESCRIPTION
		"First_source_1_branch_7_output_current"
	::= { FirstGeneral_Precision_Distribution82Analog 307 }
First_source_1_branch_8_output_current OBJECT-TYPE
	SYNTAX INTEGER
	UNITS     "0.01 "
	ACCESS read-only
	STATUS mandatory
	DESCRIPTION
		"First_source_1_branch_8_output_current"
	::= { FirstGeneral_Precision_Distribution82Analog 308 }
First_source_1_branch_9_output_current OBJECT-TYPE
	SYNTAX INTEGER
	UNITS     "0.01 "
	ACCESS read-only
	STATUS mandatory
	DESCRIPTION
		"First_source_1_branch_9_output_current"
	::= { FirstGeneral_Precision_Distribution82Analog 309 }
First_source_1_branch_10_output_current OBJECT-TYPE
	SYNTAX INTEGER
	UNITS     "0.01 "
	ACCESS read-only
	STATUS mandatory
	DESCRIPTION
		"First_source_1_branch_10_output_current"
	::= { FirstGeneral_Precision_Distribution82Analog 310 }
First_source_1_branch_11_output_current OBJECT-TYPE
	SYNTAX INTEGER
	UNITS     "0.01 "
	ACCESS read-only
	STATUS mandatory
	DESCRIPTION
		"First_source_1_branch_11_output_current"
	::= { FirstGeneral_Precision_Distribution82Analog 311 }
First_source_1_branch_12_output_current OBJECT-TYPE
	SYNTAX INTEGER
	UNITS     "0.01 "
	ACCESS read-only
	STATUS mandatory
	DESCRIPTION
		"First_source_1_branch_12_output_current"
	::= { FirstGeneral_Precision_Distribution82Analog 312 }
First_source_1_branch_13_output_current OBJECT-TYPE
	SYNTAX INTEGER
	UNITS     "0.01 "
	ACCESS read-only
	STATUS mandatory
	DESCRIPTION
		"First_source_1_branch_13_output_current"
	::= { FirstGeneral_Precision_Distribution82Analog 313 }
First_source_1_branch_14_output_current OBJECT-TYPE
	SYNTAX INTEGER
	UNITS     "0.01 "
	ACCESS read-only
	STATUS mandatory
	DESCRIPTION
		"First_source_1_branch_14_output_current"
	::= { FirstGeneral_Precision_Distribution82Analog 314 }
First_source_1_branch_15_output_current OBJECT-TYPE
	SYNTAX INTEGER
	UNITS     "0.01 "
	ACCESS read-only
	STATUS mandatory
	DESCRIPTION
		"First_source_1_branch_15_output_current"
	::= { FirstGeneral_Precision_Distribution82Analog 315 }
First_source_1_branch_16_output_current OBJECT-TYPE
	SYNTAX INTEGER
	UNITS     "0.01 "
	ACCESS read-only
	STATUS mandatory
	DESCRIPTION
		"First_source_1_branch_16_output_current"
	::= { FirstGeneral_Precision_Distribution82Analog 316 }
First_source_1_branch_17_output_current OBJECT-TYPE
	SYNTAX INTEGER
	UNITS     "0.01 "
	ACCESS read-only
	STATUS mandatory
	DESCRIPTION
		"First_source_1_branch_17_output_current"
	::= { FirstGeneral_Precision_Distribution82Analog 317 }
First_source_1_branch_18_output_current OBJECT-TYPE
	SYNTAX INTEGER
	UNITS     "0.01 "
	ACCESS read-only
	STATUS mandatory
	DESCRIPTION
		"First_source_1_branch_18_output_current"
	::= { FirstGeneral_Precision_Distribution82Analog 318 }
First_source_1_branch_19_output_current OBJECT-TYPE
	SYNTAX INTEGER
	UNITS     "0.01 "
	ACCESS read-only
	STATUS mandatory
	DESCRIPTION
		"First_source_1_branch_19_output_current"
	::= { FirstGeneral_Precision_Distribution82Analog 319 }
First_source_1_branch_20_output_current OBJECT-TYPE
	SYNTAX INTEGER
	UNITS     "0.01 "
	ACCESS read-only
	STATUS mandatory
	DESCRIPTION
		"First_source_1_branch_20_output_current"
	::= { FirstGeneral_Precision_Distribution82Analog 320 }
First_source_1_branch_21_output_current OBJECT-TYPE
	SYNTAX INTEGER
	UNITS     "0.01 "
	ACCESS read-only
	STATUS mandatory
	DESCRIPTION
		"First_source_1_branch_21_output_current"
	::= { FirstGeneral_Precision_Distribution82Analog 321 }
First_source_1_branch_22_output_current OBJECT-TYPE
	SYNTAX INTEGER
	UNITS     "0.01 "
	ACCESS read-only
	STATUS mandatory
	DESCRIPTION
		"First_source_1_branch_22_output_current"
	::= { FirstGeneral_Precision_Distribution82Analog 322 }
First_source_1_branch_23_output_current OBJECT-TYPE
	SYNTAX INTEGER
	UNITS     "0.01 "
	ACCESS read-only
	STATUS mandatory
	DESCRIPTION
		"First_source_1_branch_23_output_current"
	::= { FirstGeneral_Precision_Distribution82Analog 323 }
First_source_1_branch_24_output_current OBJECT-TYPE
	SYNTAX INTEGER
	UNITS     "0.01 "
	ACCESS read-only
	STATUS mandatory
	DESCRIPTION
		"First_source_1_branch_24_output_current"
	::= { FirstGeneral_Precision_Distribution82Analog 324 }
First_source_1_branch_25_output_current OBJECT-TYPE
	SYNTAX INTEGER
	UNITS     "0.01 "
	ACCESS read-only
	STATUS mandatory
	DESCRIPTION
		"First_source_1_branch_25_output_current"
	::= { FirstGeneral_Precision_Distribution82Analog 325 }
First_source_1_branch_26_output_current OBJECT-TYPE
	SYNTAX INTEGER
	UNITS     "0.01 "
	ACCESS read-only
	STATUS mandatory
	DESCRIPTION
		"First_source_1_branch_26_output_current"
	::= { FirstGeneral_Precision_Distribution82Analog 326 }
First_source_1_branch_27_output_current OBJECT-TYPE
	SYNTAX INTEGER
	UNITS     "0.01 "
	ACCESS read-only
	STATUS mandatory
	DESCRIPTION
		"First_source_1_branch_27_output_current"
	::= { FirstGeneral_Precision_Distribution82Analog 327 }
First_source_1_branch_28_output_current OBJECT-TYPE
	SYNTAX INTEGER
	UNITS     "0.01 "
	ACCESS read-only
	STATUS mandatory
	DESCRIPTION
		"First_source_1_branch_28_output_current"
	::= { FirstGeneral_Precision_Distribution82Analog 328 }
First_source_1_branch_29_output_current OBJECT-TYPE
	SYNTAX INTEGER
	UNITS     "0.01 "
	ACCESS read-only
	STATUS mandatory
	DESCRIPTION
		"First_source_1_branch_29_output_current"
	::= { FirstGeneral_Precision_Distribution82Analog 329 }
First_source_1_branch_30_output_current OBJECT-TYPE
	SYNTAX INTEGER
	UNITS     "0.01 "
	ACCESS read-only
	STATUS mandatory
	DESCRIPTION
		"First_source_1_branch_30_output_current"
	::= { FirstGeneral_Precision_Distribution82Analog 330 }
First_source_1_branch_31_output_current OBJECT-TYPE
	SYNTAX INTEGER
	UNITS     "0.01 "
	ACCESS read-only
	STATUS mandatory
	DESCRIPTION
		"First_source_1_branch_31_output_current"
	::= { FirstGeneral_Precision_Distribution82Analog 331 }
First_source_1_branch_32_output_current OBJECT-TYPE
	SYNTAX INTEGER
	UNITS     "0.01 "
	ACCESS read-only
	STATUS mandatory
	DESCRIPTION
		"First_source_1_branch_32_output_current"
	::= { FirstGeneral_Precision_Distribution82Analog 332 }
First_source_1_branch_33_output_current OBJECT-TYPE
	SYNTAX INTEGER
	UNITS     "0.01 "
	ACCESS read-only
	STATUS mandatory
	DESCRIPTION
		"First_source_1_branch_33_output_current"
	::= { FirstGeneral_Precision_Distribution82Analog 333 }
First_source_1_branch_34_output_current OBJECT-TYPE
	SYNTAX INTEGER
	UNITS     "0.01 "
	ACCESS read-only
	STATUS mandatory
	DESCRIPTION
		"First_source_1_branch_34_output_current"
	::= { FirstGeneral_Precision_Distribution82Analog 334 }
First_source_1_branch_35_output_current OBJECT-TYPE
	SYNTAX INTEGER
	UNITS     "0.01 "
	ACCESS read-only
	STATUS mandatory
	DESCRIPTION
		"First_source_1_branch_35_output_current"
	::= { FirstGeneral_Precision_Distribution82Analog 335 }
First_source_1_branch_36_output_current OBJECT-TYPE
	SYNTAX INTEGER
	UNITS     "0.01 "
	ACCESS read-only
	STATUS mandatory
	DESCRIPTION
		"First_source_1_branch_36_output_current"
	::= { FirstGeneral_Precision_Distribution82Analog 336 }
First_source_1_branch_37_output_current OBJECT-TYPE
	SYNTAX INTEGER
	UNITS     "0.01 "
	ACCESS read-only
	STATUS mandatory
	DESCRIPTION
		"First_source_1_branch_37_output_current"
	::= { FirstGeneral_Precision_Distribution82Analog 337 }
First_source_1_branch_38_output_current OBJECT-TYPE
	SYNTAX INTEGER
	UNITS     "0.01 "
	ACCESS read-only
	STATUS mandatory
	DESCRIPTION
		"First_source_1_branch_38_output_current"
	::= { FirstGeneral_Precision_Distribution82Analog 338 }
First_source_1_branch_39_output_current OBJECT-TYPE
	SYNTAX INTEGER
	UNITS     "0.01 "
	ACCESS read-only
	STATUS mandatory
	DESCRIPTION
		"First_source_1_branch_39_output_current"
	::= { FirstGeneral_Precision_Distribution82Analog 339 }
First_source_1_branch_40_output_current OBJECT-TYPE
	SYNTAX INTEGER
	UNITS     "0.01 "
	ACCESS read-only
	STATUS mandatory
	DESCRIPTION
		"First_source_1_branch_40_output_current"
	::= { FirstGeneral_Precision_Distribution82Analog 340 }
First_source_1_branch_41_output_current OBJECT-TYPE
	SYNTAX INTEGER
	UNITS     "0.01 "
	ACCESS read-only
	STATUS mandatory
	DESCRIPTION
		"First_source_1_branch_41_output_current"
	::= { FirstGeneral_Precision_Distribution82Analog 341 }
First_source_1_branch_42_output_current OBJECT-TYPE
	SYNTAX INTEGER
	UNITS     "0.01 "
	ACCESS read-only
	STATUS mandatory
	DESCRIPTION
		"First_source_1_branch_42_output_current"
	::= { FirstGeneral_Precision_Distribution82Analog 342 }
First_source_1_branch_43_output_current OBJECT-TYPE
	SYNTAX INTEGER
	UNITS     "0.01 "
	ACCESS read-only
	STATUS mandatory
	DESCRIPTION
		"First_source_1_branch_43_output_current"
	::= { FirstGeneral_Precision_Distribution82Analog 343 }
First_source_1_branch_44_output_current OBJECT-TYPE
	SYNTAX INTEGER
	UNITS     "0.01 "
	ACCESS read-only
	STATUS mandatory
	DESCRIPTION
		"First_source_1_branch_44_output_current"
	::= { FirstGeneral_Precision_Distribution82Analog 344 }
First_source_1_branch_45_output_current OBJECT-TYPE
	SYNTAX INTEGER
	UNITS     "0.01 "
	ACCESS read-only
	STATUS mandatory
	DESCRIPTION
		"First_source_1_branch_45_output_current"
	::= { FirstGeneral_Precision_Distribution82Analog 345 }
First_source_1_branch_46_output_current OBJECT-TYPE
	SYNTAX INTEGER
	UNITS     "0.01 "
	ACCESS read-only
	STATUS mandatory
	DESCRIPTION
		"First_source_1_branch_46_output_current"
	::= { FirstGeneral_Precision_Distribution82Analog 346 }
First_source_1_branch_47_output_current OBJECT-TYPE
	SYNTAX INTEGER
	UNITS     "0.01 "
	ACCESS read-only
	STATUS mandatory
	DESCRIPTION
		"First_source_1_branch_47_output_current"
	::= { FirstGeneral_Precision_Distribution82Analog 347 }
First_source_1_branch_48_output_current OBJECT-TYPE
	SYNTAX INTEGER
	UNITS     "0.01 "
	ACCESS read-only
	STATUS mandatory
	DESCRIPTION
		"First_source_1_branch_48_output_current"
	::= { FirstGeneral_Precision_Distribution82Analog 348 }
First_source_1_branch_49_output_current OBJECT-TYPE
	SYNTAX INTEGER
	UNITS     "0.01 "
	ACCESS read-only
	STATUS mandatory
	DESCRIPTION
		"First_source_1_branch_49_output_current"
	::= { FirstGeneral_Precision_Distribution82Analog 349 }
First_source_1_branch_50_output_current OBJECT-TYPE
	SYNTAX INTEGER
	UNITS     "0.01 "
	ACCESS read-only
	STATUS mandatory
	DESCRIPTION
		"First_source_1_branch_50_output_current"
	::= { FirstGeneral_Precision_Distribution82Analog 350 }
First_source_1_branch_51_output_current OBJECT-TYPE
	SYNTAX INTEGER
	UNITS     "0.01 "
	ACCESS read-only
	STATUS mandatory
	DESCRIPTION
		"First_source_1_branch_51_output_current"
	::= { FirstGeneral_Precision_Distribution82Analog 351 }
First_source_1_branch_52_output_current OBJECT-TYPE
	SYNTAX INTEGER
	UNITS     "0.01 "
	ACCESS read-only
	STATUS mandatory
	DESCRIPTION
		"First_source_1_branch_52_output_current"
	::= { FirstGeneral_Precision_Distribution82Analog 352 }
First_source_1_branch_53_output_current OBJECT-TYPE
	SYNTAX INTEGER
	UNITS     "0.01 "
	ACCESS read-only
	STATUS mandatory
	DESCRIPTION
		"First_source_1_branch_53_output_current"
	::= { FirstGeneral_Precision_Distribution82Analog 353 }
First_source_1_branch_54_output_current OBJECT-TYPE
	SYNTAX INTEGER
	UNITS     "0.01 "
	ACCESS read-only
	STATUS mandatory
	DESCRIPTION
		"First_source_1_branch_54_output_current"
	::= { FirstGeneral_Precision_Distribution82Analog 354 }
First_source_1_branch_55_output_current OBJECT-TYPE
	SYNTAX INTEGER
	UNITS     "0.01 "
	ACCESS read-only
	STATUS mandatory
	DESCRIPTION
		"First_source_1_branch_55_output_current"
	::= { FirstGeneral_Precision_Distribution82Analog 355 }
First_source_1_branch_56_output_current OBJECT-TYPE
	SYNTAX INTEGER
	UNITS     "0.01 "
	ACCESS read-only
	STATUS mandatory
	DESCRIPTION
		"First_source_1_branch_56_output_current"
	::= { FirstGeneral_Precision_Distribution82Analog 356 }
First_source_1_branch_57_output_current OBJECT-TYPE
	SYNTAX INTEGER
	UNITS     "0.01 "
	ACCESS read-only
	STATUS mandatory
	DESCRIPTION
		"First_source_1_branch_57_output_current"
	::= { FirstGeneral_Precision_Distribution82Analog 357 }
First_source_1_branch_58_output_current OBJECT-TYPE
	SYNTAX INTEGER
	UNITS     "0.01 "
	ACCESS read-only
	STATUS mandatory
	DESCRIPTION
		"First_source_1_branch_58_output_current"
	::= { FirstGeneral_Precision_Distribution82Analog 358 }
First_source_1_branch_59_output_current OBJECT-TYPE
	SYNTAX INTEGER
	UNITS     "0.01 "
	ACCESS read-only
	STATUS mandatory
	DESCRIPTION
		"First_source_1_branch_59_output_current"
	::= { FirstGeneral_Precision_Distribution82Analog 359 }
First_source_1_branch_60_output_current OBJECT-TYPE
	SYNTAX INTEGER
	UNITS     "0.01 "
	ACCESS read-only
	STATUS mandatory
	DESCRIPTION
		"First_source_1_branch_60_output_current"
	::= { FirstGeneral_Precision_Distribution82Analog 360 }
First_source_1_branch_61_output_current OBJECT-TYPE
	SYNTAX INTEGER
	UNITS     "0.01 "
	ACCESS read-only
	STATUS mandatory
	DESCRIPTION
		"First_source_1_branch_61_output_current"
	::= { FirstGeneral_Precision_Distribution82Analog 361 }
First_source_1_branch_62_output_current OBJECT-TYPE
	SYNTAX INTEGER
	UNITS     "0.01 "
	ACCESS read-only
	STATUS mandatory
	DESCRIPTION
		"First_source_1_branch_62_output_current"
	::= { FirstGeneral_Precision_Distribution82Analog 362 }
First_source_1_branch_63_output_current OBJECT-TYPE
	SYNTAX INTEGER
	UNITS     "0.01 "
	ACCESS read-only
	STATUS mandatory
	DESCRIPTION
		"First_source_1_branch_63_output_current"
	::= { FirstGeneral_Precision_Distribution82Analog 363 }
First_source_1_branch_64_output_current OBJECT-TYPE
	SYNTAX INTEGER
	UNITS     "0.01 "
	ACCESS read-only
	STATUS mandatory
	DESCRIPTION
		"First_source_1_branch_64_output_current"
	::= { FirstGeneral_Precision_Distribution82Analog 364 }
First_source_1_branch_65_output_current OBJECT-TYPE
	SYNTAX INTEGER
	UNITS     "0.01 "
	ACCESS read-only
	STATUS mandatory
	DESCRIPTION
		"First_source_1_branch_65_output_current"
	::= { FirstGeneral_Precision_Distribution82Analog 365 }
First_source_1_branch_66_output_current OBJECT-TYPE
	SYNTAX INTEGER
	UNITS     "0.01 "
	ACCESS read-only
	STATUS mandatory
	DESCRIPTION
		"First_source_1_branch_66_output_current"
	::= { FirstGeneral_Precision_Distribution82Analog 366 }
First_source_1_branch_67_output_current OBJECT-TYPE
	SYNTAX INTEGER
	UNITS     "0.01 "
	ACCESS read-only
	STATUS mandatory
	DESCRIPTION
		"First_source_1_branch_67_output_current"
	::= { FirstGeneral_Precision_Distribution82Analog 367 }
First_source_1_branch_68_output_current OBJECT-TYPE
	SYNTAX INTEGER
	UNITS     "0.01 "
	ACCESS read-only
	STATUS mandatory
	DESCRIPTION
		"First_source_1_branch_68_output_current"
	::= { FirstGeneral_Precision_Distribution82Analog 368 }
First_source_1_branch_69_output_current OBJECT-TYPE
	SYNTAX INTEGER
	UNITS     "0.01 "
	ACCESS read-only
	STATUS mandatory
	DESCRIPTION
		"First_source_1_branch_69_output_current"
	::= { FirstGeneral_Precision_Distribution82Analog 369 }
First_source_1_branch_70_output_current OBJECT-TYPE
	SYNTAX INTEGER
	UNITS     "0.01 "
	ACCESS read-only
	STATUS mandatory
	DESCRIPTION
		"First_source_1_branch_70_output_current"
	::= { FirstGeneral_Precision_Distribution82Analog 370 }
First_source_1_branch_71_output_current OBJECT-TYPE
	SYNTAX INTEGER
	UNITS     "0.01 "
	ACCESS read-only
	STATUS mandatory
	DESCRIPTION
		"First_source_1_branch_71_output_current"
	::= { FirstGeneral_Precision_Distribution82Analog 371 }
First_source_1_branch_72_output_current OBJECT-TYPE
	SYNTAX INTEGER
	UNITS     "0.01 "
	ACCESS read-only
	STATUS mandatory
	DESCRIPTION
		"First_source_1_branch_72_output_current"
	::= { FirstGeneral_Precision_Distribution82Analog 372 }
First_source_1_branch_73_output_current OBJECT-TYPE
	SYNTAX INTEGER
	UNITS     "0.01 "
	ACCESS read-only
	STATUS mandatory
	DESCRIPTION
		"First_source_1_branch_73_output_current"
	::= { FirstGeneral_Precision_Distribution82Analog 373 }
First_source_1_branch_74_output_current OBJECT-TYPE
	SYNTAX INTEGER
	UNITS     "0.01 "
	ACCESS read-only
	STATUS mandatory
	DESCRIPTION
		"First_source_1_branch_74_output_current"
	::= { FirstGeneral_Precision_Distribution82Analog 374 }
First_source_1_branch_75_output_current OBJECT-TYPE
	SYNTAX INTEGER
	UNITS     "0.01 "
	ACCESS read-only
	STATUS mandatory
	DESCRIPTION
		"First_source_1_branch_75_output_current"
	::= { FirstGeneral_Precision_Distribution82Analog 375 }
First_source_1_branch_76_output_current OBJECT-TYPE
	SYNTAX INTEGER
	UNITS     "0.01 "
	ACCESS read-only
	STATUS mandatory
	DESCRIPTION
		"First_source_1_branch_76_output_current"
	::= { FirstGeneral_Precision_Distribution82Analog 376 }
First_source_1_branch_77_output_current OBJECT-TYPE
	SYNTAX INTEGER
	UNITS     "0.01 "
	ACCESS read-only
	STATUS mandatory
	DESCRIPTION
		"First_source_1_branch_77_output_current"
	::= { FirstGeneral_Precision_Distribution82Analog 377 }
First_source_1_branch_78_output_current OBJECT-TYPE
	SYNTAX INTEGER
	UNITS     "0.01 "
	ACCESS read-only
	STATUS mandatory
	DESCRIPTION
		"First_source_1_branch_78_output_current"
	::= { FirstGeneral_Precision_Distribution82Analog 378 }
First_source_1_branch_79_output_current OBJECT-TYPE
	SYNTAX INTEGER
	UNITS     "0.01 "
	ACCESS read-only
	STATUS mandatory
	DESCRIPTION
		"First_source_1_branch_79_output_current"
	::= { FirstGeneral_Precision_Distribution82Analog 379 }
First_source_1_branch_80_output_current OBJECT-TYPE
	SYNTAX INTEGER
	UNITS     "0.01 "
	ACCESS read-only
	STATUS mandatory
	DESCRIPTION
		"First_source_1_branch_80_output_current"
	::= { FirstGeneral_Precision_Distribution82Analog 380 }
First_source_1_branch_81_output_current OBJECT-TYPE
	SYNTAX INTEGER
	UNITS     "0.01 "
	ACCESS read-only
	STATUS mandatory
	DESCRIPTION
		"First_source_1_branch_81_output_current"
	::= { FirstGeneral_Precision_Distribution82Analog 381 }
First_source_1_branch_82_output_current OBJECT-TYPE
	SYNTAX INTEGER
	UNITS     "0.01 "
	ACCESS read-only
	STATUS mandatory
	DESCRIPTION
		"First_source_1_branch_82_output_current"
	::= { FirstGeneral_Precision_Distribution82Analog 382 }
First_source_1_branch_83_output_current OBJECT-TYPE
	SYNTAX INTEGER
	UNITS     "0.01 "
	ACCESS read-only
	STATUS mandatory
	DESCRIPTION
		"First_source_1_branch_83_output_current"
	::= { FirstGeneral_Precision_Distribution82Analog 383 }
First_source_1_branch_84_output_current OBJECT-TYPE
	SYNTAX INTEGER
	UNITS     "0.01 "
	ACCESS read-only
	STATUS mandatory
	DESCRIPTION
		"First_source_1_branch_84_output_current"
	::= { FirstGeneral_Precision_Distribution82Analog 384 }
First_source_1_branch_85_output_current OBJECT-TYPE
	SYNTAX INTEGER
	UNITS     "0.01 "
	ACCESS read-only
	STATUS mandatory
	DESCRIPTION
		"First_source_1_branch_85_output_current"
	::= { FirstGeneral_Precision_Distribution82Analog 385 }
First_source_1_branch_86_output_current OBJECT-TYPE
	SYNTAX INTEGER
	UNITS     "0.01 "
	ACCESS read-only
	STATUS mandatory
	DESCRIPTION
		"First_source_1_branch_86_output_current"
	::= { FirstGeneral_Precision_Distribution82Analog 386 }
First_source_1_branch_87_output_current OBJECT-TYPE
	SYNTAX INTEGER
	UNITS     "0.01 "
	ACCESS read-only
	STATUS mandatory
	DESCRIPTION
		"First_source_1_branch_87_output_current"
	::= { FirstGeneral_Precision_Distribution82Analog 387 }
First_source_1_branch_88_output_current OBJECT-TYPE
	SYNTAX INTEGER
	UNITS     "0.01 "
	ACCESS read-only
	STATUS mandatory
	DESCRIPTION
		"First_source_1_branch_88_output_current"
	::= { FirstGeneral_Precision_Distribution82Analog 388 }
First_source_1_branch_89_output_current OBJECT-TYPE
	SYNTAX INTEGER
	UNITS     "0.01 "
	ACCESS read-only
	STATUS mandatory
	DESCRIPTION
		"First_source_1_branch_89_output_current"
	::= { FirstGeneral_Precision_Distribution82Analog 389 }
First_source_1_branch_90_output_current OBJECT-TYPE
	SYNTAX INTEGER
	UNITS     "0.01 "
	ACCESS read-only
	STATUS mandatory
	DESCRIPTION
		"First_source_1_branch_90_output_current"
	::= { FirstGeneral_Precision_Distribution82Analog 390 }
First_source_1_branch_91_output_current OBJECT-TYPE
	SYNTAX INTEGER
	UNITS     "0.01 "
	ACCESS read-only
	STATUS mandatory
	DESCRIPTION
		"First_source_1_branch_91_output_current"
	::= { FirstGeneral_Precision_Distribution82Analog 391 }
First_source_1_branch_92_output_current OBJECT-TYPE
	SYNTAX INTEGER
	UNITS     "0.01 "
	ACCESS read-only
	STATUS mandatory
	DESCRIPTION
		"First_source_1_branch_92_output_current"
	::= { FirstGeneral_Precision_Distribution82Analog 392 }
First_source_1_branch_93_output_current OBJECT-TYPE
	SYNTAX INTEGER
	UNITS     "0.01 "
	ACCESS read-only
	STATUS mandatory
	DESCRIPTION
		"First_source_1_branch_93_output_current"
	::= { FirstGeneral_Precision_Distribution82Analog 393 }
First_source_1_branch_94_output_current OBJECT-TYPE
	SYNTAX INTEGER
	UNITS     "0.01 "
	ACCESS read-only
	STATUS mandatory
	DESCRIPTION
		"First_source_1_branch_94_output_current"
	::= { FirstGeneral_Precision_Distribution82Analog 394 }
First_source_1_branch_95_output_current OBJECT-TYPE
	SYNTAX INTEGER
	UNITS     "0.01 "
	ACCESS read-only
	STATUS mandatory
	DESCRIPTION
		"First_source_1_branch_95_output_current"
	::= { FirstGeneral_Precision_Distribution82Analog 395 }
First_source_1_branch_96_output_current OBJECT-TYPE
	SYNTAX INTEGER
	UNITS     "0.01 "
	ACCESS read-only
	STATUS mandatory
	DESCRIPTION
		"First_source_1_branch_96_output_current"
	::= { FirstGeneral_Precision_Distribution82Analog 396 }
First_source_1_branch_97_output_current OBJECT-TYPE
	SYNTAX INTEGER
	UNITS     "0.01 "
	ACCESS read-only
	STATUS mandatory
	DESCRIPTION
		"First_source_1_branch_97_output_current"
	::= { FirstGeneral_Precision_Distribution82Analog 397 }
First_source_1_branch_98_output_current OBJECT-TYPE
	SYNTAX INTEGER
	UNITS     "0.01 "
	ACCESS read-only
	STATUS mandatory
	DESCRIPTION
		"First_source_1_branch_98_output_current"
	::= { FirstGeneral_Precision_Distribution82Analog 398 }
First_source_1_branch_99_output_current OBJECT-TYPE
	SYNTAX INTEGER
	UNITS     "0.01 "
	ACCESS read-only
	STATUS mandatory
	DESCRIPTION
		"First_source_1_branch_99_output_current"
	::= { FirstGeneral_Precision_Distribution82Analog 399 }
First_source_1_branch_100_output_current OBJECT-TYPE
	SYNTAX INTEGER
	UNITS     "0.01 "
	ACCESS read-only
	STATUS mandatory
	DESCRIPTION
		"First_source_1_branch_100_output_current"
	::= { FirstGeneral_Precision_Distribution82Analog 400 }
First_source_1_branch_1_output_power OBJECT-TYPE
	SYNTAX INTEGER
	UNITS     "0.01 "
	ACCESS read-only
	STATUS mandatory
	DESCRIPTION
		"First_source_1_branch_1_output_power"
	::= { FirstGeneral_Precision_Distribution82Analog 401 }
First_source_1_branch_2_output_power OBJECT-TYPE
	SYNTAX INTEGER
	UNITS     "0.01KW "
	ACCESS read-only
	STATUS mandatory
	DESCRIPTION
		"First_source_1_branch_2_output_power"
	::= { FirstGeneral_Precision_Distribution82Analog 402 }
First_source_1_branch_3_output_power OBJECT-TYPE
	SYNTAX INTEGER
	UNITS     "0.01 "
	ACCESS read-only
	STATUS mandatory
	DESCRIPTION
		"First_source_1_branch_3_output_power"
	::= { FirstGeneral_Precision_Distribution82Analog 403 }
First_source_1_branch_4_output_power OBJECT-TYPE
	SYNTAX INTEGER
	UNITS     "0.01 "
	ACCESS read-only
	STATUS mandatory
	DESCRIPTION
		"First_source_1_branch_4_output_power"
	::= { FirstGeneral_Precision_Distribution82Analog 404 }
First_source_1_branch_5_output_power OBJECT-TYPE
	SYNTAX INTEGER
	UNITS     "0.01 "
	ACCESS read-only
	STATUS mandatory
	DESCRIPTION
		"First_source_1_branch_5_output_power"
	::= { FirstGeneral_Precision_Distribution82Analog 405 }
First_source_1_branch_6_output_power OBJECT-TYPE
	SYNTAX INTEGER
	UNITS     "0.01 "
	ACCESS read-only
	STATUS mandatory
	DESCRIPTION
		"First_source_1_branch_6_output_power"
	::= { FirstGeneral_Precision_Distribution82Analog 406 }
First_source_1_branch_7_output_power OBJECT-TYPE
	SYNTAX INTEGER
	UNITS     "0.01 "
	ACCESS read-only
	STATUS mandatory
	DESCRIPTION
		"First_source_1_branch_7_output_power"
	::= { FirstGeneral_Precision_Distribution82Analog 407 }
First_source_1_branch_8_output_power OBJECT-TYPE
	SYNTAX INTEGER
	UNITS     "0.01 "
	ACCESS read-only
	STATUS mandatory
	DESCRIPTION
		"First_source_1_branch_8_output_power"
	::= { FirstGeneral_Precision_Distribution82Analog 408 }
First_source_1_branch_9_output_power OBJECT-TYPE
	SYNTAX INTEGER
	UNITS     "0.01 "
	ACCESS read-only
	STATUS mandatory
	DESCRIPTION
		"First_source_1_branch_9_output_power"
	::= { FirstGeneral_Precision_Distribution82Analog 409 }
First_source_1_branch_10_output_power OBJECT-TYPE
	SYNTAX INTEGER
	UNITS     "0.01 "
	ACCESS read-only
	STATUS mandatory
	DESCRIPTION
		"First_source_1_branch_10_output_power"
	::= { FirstGeneral_Precision_Distribution82Analog 410 }
First_source_1_branch_11_output_power OBJECT-TYPE
	SYNTAX INTEGER
	UNITS     "0.01 "
	ACCESS read-only
	STATUS mandatory
	DESCRIPTION
		"First_source_1_branch_11_output_power"
	::= { FirstGeneral_Precision_Distribution82Analog 411 }
First_source_1_branch_12_output_power OBJECT-TYPE
	SYNTAX INTEGER
	UNITS     "0.01 "
	ACCESS read-only
	STATUS mandatory
	DESCRIPTION
		"First_source_1_branch_12_output_power"
	::= { FirstGeneral_Precision_Distribution82Analog 412 }
First_source_1_branch_13_output_power OBJECT-TYPE
	SYNTAX INTEGER
	UNITS     "0.01 "
	ACCESS read-only
	STATUS mandatory
	DESCRIPTION
		"First_source_1_branch_13_output_power"
	::= { FirstGeneral_Precision_Distribution82Analog 413 }
First_source_1_branch_14_output_power OBJECT-TYPE
	SYNTAX INTEGER
	UNITS     "0.01 "
	ACCESS read-only
	STATUS mandatory
	DESCRIPTION
		"First_source_1_branch_14_output_power"
	::= { FirstGeneral_Precision_Distribution82Analog 414 }
First_source_1_branch_15_output_power OBJECT-TYPE
	SYNTAX INTEGER
	UNITS     "0.01 "
	ACCESS read-only
	STATUS mandatory
	DESCRIPTION
		"First_source_1_branch_15_output_power"
	::= { FirstGeneral_Precision_Distribution82Analog 415 }
First_source_1_branch_16_output_power OBJECT-TYPE
	SYNTAX INTEGER
	UNITS     "0.01 "
	ACCESS read-only
	STATUS mandatory
	DESCRIPTION
		"First_source_1_branch_16_output_power"
	::= { FirstGeneral_Precision_Distribution82Analog 416 }
First_source_1_branch_17_output_power OBJECT-TYPE
	SYNTAX INTEGER
	UNITS     "0.01 "
	ACCESS read-only
	STATUS mandatory
	DESCRIPTION
		"First_source_1_branch_17_output_power"
	::= { FirstGeneral_Precision_Distribution82Analog 417 }
First_source_1_branch_18_output_power OBJECT-TYPE
	SYNTAX INTEGER
	UNITS     "0.01 "
	ACCESS read-only
	STATUS mandatory
	DESCRIPTION
		"First_source_1_branch_18_output_power"
	::= { FirstGeneral_Precision_Distribution82Analog 418 }
First_source_1_branch_19_output_power OBJECT-TYPE
	SYNTAX INTEGER
	UNITS     "0.01 "
	ACCESS read-only
	STATUS mandatory
	DESCRIPTION
		"First_source_1_branch_19_output_power"
	::= { FirstGeneral_Precision_Distribution82Analog 419 }
First_source_1_branch_20_output_power OBJECT-TYPE
	SYNTAX INTEGER
	UNITS     "0.01 "
	ACCESS read-only
	STATUS mandatory
	DESCRIPTION
		"First_source_1_branch_20_output_power"
	::= { FirstGeneral_Precision_Distribution82Analog 420 }
First_source_1_branch_21_output_power OBJECT-TYPE
	SYNTAX INTEGER
	UNITS     "0.01 "
	ACCESS read-only
	STATUS mandatory
	DESCRIPTION
		"First_source_1_branch_21_output_power"
	::= { FirstGeneral_Precision_Distribution82Analog 421 }
First_source_1_branch_22_output_power OBJECT-TYPE
	SYNTAX INTEGER
	UNITS     "0.01 "
	ACCESS read-only
	STATUS mandatory
	DESCRIPTION
		"First_source_1_branch_22_output_power"
	::= { FirstGeneral_Precision_Distribution82Analog 422 }
First_source_1_branch_23_output_power OBJECT-TYPE
	SYNTAX INTEGER
	UNITS     "0.01 "
	ACCESS read-only
	STATUS mandatory
	DESCRIPTION
		"First_source_1_branch_23_output_power"
	::= { FirstGeneral_Precision_Distribution82Analog 423 }
First_source_1_branch_24_output_power OBJECT-TYPE
	SYNTAX INTEGER
	UNITS     "0.01 "
	ACCESS read-only
	STATUS mandatory
	DESCRIPTION
		"First_source_1_branch_24_output_power"
	::= { FirstGeneral_Precision_Distribution82Analog 424 }
First_source_1_branch_25_output_power OBJECT-TYPE
	SYNTAX INTEGER
	UNITS     "0.01 "
	ACCESS read-only
	STATUS mandatory
	DESCRIPTION
		"First_source_1_branch_25_output_power"
	::= { FirstGeneral_Precision_Distribution82Analog 425 }
First_source_1_branch_26_output_power OBJECT-TYPE
	SYNTAX INTEGER
	UNITS     "0.01 "
	ACCESS read-only
	STATUS mandatory
	DESCRIPTION
		"First_source_1_branch_26_output_power"
	::= { FirstGeneral_Precision_Distribution82Analog 426 }
First_source_1_branch_27_output_power OBJECT-TYPE
	SYNTAX INTEGER
	UNITS     "0.01 "
	ACCESS read-only
	STATUS mandatory
	DESCRIPTION
		"First_source_1_branch_27_output_power"
	::= { FirstGeneral_Precision_Distribution82Analog 427 }
First_source_1_branch_28_output_power OBJECT-TYPE
	SYNTAX INTEGER
	UNITS     "0.01 "
	ACCESS read-only
	STATUS mandatory
	DESCRIPTION
		"First_source_1_branch_28_output_power"
	::= { FirstGeneral_Precision_Distribution82Analog 428 }
First_source_1_branch_29_output_power OBJECT-TYPE
	SYNTAX INTEGER
	UNITS     "0.01 "
	ACCESS read-only
	STATUS mandatory
	DESCRIPTION
		"First_source_1_branch_29_output_power"
	::= { FirstGeneral_Precision_Distribution82Analog 429 }
First_source_1_branch_30_output_power OBJECT-TYPE
	SYNTAX INTEGER
	UNITS     "0.01 "
	ACCESS read-only
	STATUS mandatory
	DESCRIPTION
		"First_source_1_branch_30_output_power"
	::= { FirstGeneral_Precision_Distribution82Analog 430 }
First_source_1_branch_31_output_power OBJECT-TYPE
	SYNTAX INTEGER
	UNITS     "0.01 "
	ACCESS read-only
	STATUS mandatory
	DESCRIPTION
		"First_source_1_branch_31_output_power"
	::= { FirstGeneral_Precision_Distribution82Analog 431 }
First_source_1_branch_32_output_power OBJECT-TYPE
	SYNTAX INTEGER
	UNITS     "0.01 "
	ACCESS read-only
	STATUS mandatory
	DESCRIPTION
		"First_source_1_branch_32_output_power"
	::= { FirstGeneral_Precision_Distribution82Analog 432 }
First_source_1_branch_33_output_power OBJECT-TYPE
	SYNTAX INTEGER
	UNITS     "0.01 "
	ACCESS read-only
	STATUS mandatory
	DESCRIPTION
		"First_source_1_branch_33_output_power"
	::= { FirstGeneral_Precision_Distribution82Analog 433 }
First_source_1_branch_34_output_power OBJECT-TYPE
	SYNTAX INTEGER
	UNITS     "0.01 "
	ACCESS read-only
	STATUS mandatory
	DESCRIPTION
		"First_source_1_branch_34_output_power"
	::= { FirstGeneral_Precision_Distribution82Analog 434 }
First_source_1_branch_35_output_power OBJECT-TYPE
	SYNTAX INTEGER
	UNITS     "0.01 "
	ACCESS read-only
	STATUS mandatory
	DESCRIPTION
		"First_source_1_branch_35_output_power"
	::= { FirstGeneral_Precision_Distribution82Analog 435 }
First_source_1_branch_36_output_power OBJECT-TYPE
	SYNTAX INTEGER
	UNITS     "0.01 "
	ACCESS read-only
	STATUS mandatory
	DESCRIPTION
		"First_source_1_branch_36_output_power"
	::= { FirstGeneral_Precision_Distribution82Analog 436 }
First_source_1_branch_37_output_power OBJECT-TYPE
	SYNTAX INTEGER
	UNITS     "0.01 "
	ACCESS read-only
	STATUS mandatory
	DESCRIPTION
		"First_source_1_branch_37_output_power"
	::= { FirstGeneral_Precision_Distribution82Analog 437 }
First_source_1_branch_38_output_power OBJECT-TYPE
	SYNTAX INTEGER
	UNITS     "0.01 "
	ACCESS read-only
	STATUS mandatory
	DESCRIPTION
		"First_source_1_branch_38_output_power"
	::= { FirstGeneral_Precision_Distribution82Analog 438 }
First_source_1_branch_39_output_power OBJECT-TYPE
	SYNTAX INTEGER
	UNITS     "0.01 "
	ACCESS read-only
	STATUS mandatory
	DESCRIPTION
		"First_source_1_branch_39_output_power"
	::= { FirstGeneral_Precision_Distribution82Analog 439 }
First_source_1_branch_40_output_power OBJECT-TYPE
	SYNTAX INTEGER
	UNITS     "0.01 "
	ACCESS read-only
	STATUS mandatory
	DESCRIPTION
		"First_source_1_branch_40_output_power"
	::= { FirstGeneral_Precision_Distribution82Analog 440 }
First_source_1_branch_41_output_power OBJECT-TYPE
	SYNTAX INTEGER
	UNITS     "0.01 "
	ACCESS read-only
	STATUS mandatory
	DESCRIPTION
		"First_source_1_branch_41_output_power"
	::= { FirstGeneral_Precision_Distribution82Analog 441 }
First_source_1_branch_42_output_power OBJECT-TYPE
	SYNTAX INTEGER
	UNITS     "0.01 "
	ACCESS read-only
	STATUS mandatory
	DESCRIPTION
		"First_source_1_branch_42_output_power"
	::= { FirstGeneral_Precision_Distribution82Analog 442 }
First_source_1_branch_43_output_power OBJECT-TYPE
	SYNTAX INTEGER
	UNITS     "0.01 "
	ACCESS read-only
	STATUS mandatory
	DESCRIPTION
		"First_source_1_branch_43_output_power"
	::= { FirstGeneral_Precision_Distribution82Analog 443 }
First_source_1_branch_44_output_power OBJECT-TYPE
	SYNTAX INTEGER
	UNITS     "0.01 "
	ACCESS read-only
	STATUS mandatory
	DESCRIPTION
		"First_source_1_branch_44_output_power"
	::= { FirstGeneral_Precision_Distribution82Analog 444 }
First_source_1_branch_45_output_power OBJECT-TYPE
	SYNTAX INTEGER
	UNITS     "0.01 "
	ACCESS read-only
	STATUS mandatory
	DESCRIPTION
		"First_source_1_branch_45_output_power"
	::= { FirstGeneral_Precision_Distribution82Analog 445 }
First_source_1_branch_46_output_power OBJECT-TYPE
	SYNTAX INTEGER
	UNITS     "0.01 "
	ACCESS read-only
	STATUS mandatory
	DESCRIPTION
		"First_source_1_branch_46_output_power"
	::= { FirstGeneral_Precision_Distribution82Analog 446 }
First_source_1_branch_47_output_power OBJECT-TYPE
	SYNTAX INTEGER
	UNITS     "0.01 "
	ACCESS read-only
	STATUS mandatory
	DESCRIPTION
		"First_source_1_branch_47_output_power"
	::= { FirstGeneral_Precision_Distribution82Analog 447 }
First_source_1_branch_48_output_power OBJECT-TYPE
	SYNTAX INTEGER
	UNITS     "0.01 "
	ACCESS read-only
	STATUS mandatory
	DESCRIPTION
		"First_source_1_branch_48_output_power"
	::= { FirstGeneral_Precision_Distribution82Analog 448 }
First_source_1_branch_49_output_power OBJECT-TYPE
	SYNTAX INTEGER
	UNITS     "0.01 "
	ACCESS read-only
	STATUS mandatory
	DESCRIPTION
		"First_source_1_branch_49_output_power"
	::= { FirstGeneral_Precision_Distribution82Analog 449 }
First_source_1_branch_50_output_power OBJECT-TYPE
	SYNTAX INTEGER
	UNITS     "0.01 "
	ACCESS read-only
	STATUS mandatory
	DESCRIPTION
		"First_source_1_branch_50_output_power"
	::= { FirstGeneral_Precision_Distribution82Analog 450 }
First_source_1_branch_51_output_power OBJECT-TYPE
	SYNTAX INTEGER
	UNITS     "0.01 "
	ACCESS read-only
	STATUS mandatory
	DESCRIPTION
		"First_source_1_branch_51_output_power"
	::= { FirstGeneral_Precision_Distribution82Analog 451 }
First_source_1_branch_52_output_power OBJECT-TYPE
	SYNTAX INTEGER
	UNITS     "0.01 "
	ACCESS read-only
	STATUS mandatory
	DESCRIPTION
		"First_source_1_branch_52_output_power"
	::= { FirstGeneral_Precision_Distribution82Analog 452 }
First_source_1_branch_53_output_power OBJECT-TYPE
	SYNTAX INTEGER
	UNITS     "0.01 "
	ACCESS read-only
	STATUS mandatory
	DESCRIPTION
		"First_source_1_branch_53_output_power"
	::= { FirstGeneral_Precision_Distribution82Analog 453 }
First_source_1_branch_54_output_power OBJECT-TYPE
	SYNTAX INTEGER
	UNITS     "0.01 "
	ACCESS read-only
	STATUS mandatory
	DESCRIPTION
		"First_source_1_branch_54_output_power"
	::= { FirstGeneral_Precision_Distribution82Analog 454 }
First_source_1_branch_55_output_power OBJECT-TYPE
	SYNTAX INTEGER
	UNITS     "0.01 "
	ACCESS read-only
	STATUS mandatory
	DESCRIPTION
		"First_source_1_branch_55_output_power"
	::= { FirstGeneral_Precision_Distribution82Analog 455 }
First_source_1_branch_56_output_power OBJECT-TYPE
	SYNTAX INTEGER
	UNITS     "0.01 "
	ACCESS read-only
	STATUS mandatory
	DESCRIPTION
		"First_source_1_branch_56_output_power"
	::= { FirstGeneral_Precision_Distribution82Analog 456 }
First_source_1_branch_57_output_power OBJECT-TYPE
	SYNTAX INTEGER
	UNITS     "0.01 "
	ACCESS read-only
	STATUS mandatory
	DESCRIPTION
		"First_source_1_branch_57_output_power"
	::= { FirstGeneral_Precision_Distribution82Analog 457 }
First_source_1_branch_58_output_power OBJECT-TYPE
	SYNTAX INTEGER
	UNITS     "0.01 "
	ACCESS read-only
	STATUS mandatory
	DESCRIPTION
		"First_source_1_branch_58_output_power"
	::= { FirstGeneral_Precision_Distribution82Analog 458 }
First_source_1_branch_59_output_power OBJECT-TYPE
	SYNTAX INTEGER
	UNITS     "0.01 "
	ACCESS read-only
	STATUS mandatory
	DESCRIPTION
		"First_source_1_branch_59_output_power"
	::= { FirstGeneral_Precision_Distribution82Analog 459 }
First_source_1_branch_60_output_power OBJECT-TYPE
	SYNTAX INTEGER
	UNITS     "0.01 "
	ACCESS read-only
	STATUS mandatory
	DESCRIPTION
		"First_source_1_branch_60_output_power"
	::= { FirstGeneral_Precision_Distribution82Analog 460 }
First_source_1_branch_61_output_power OBJECT-TYPE
	SYNTAX INTEGER
	UNITS     "0.01 "
	ACCESS read-only
	STATUS mandatory
	DESCRIPTION
		"First_source_1_branch_61_output_power"
	::= { FirstGeneral_Precision_Distribution82Analog 461 }
First_source_1_branch_62_output_power OBJECT-TYPE
	SYNTAX INTEGER
	UNITS     "0.01 "
	ACCESS read-only
	STATUS mandatory
	DESCRIPTION
		"First_source_1_branch_62_output_power"
	::= { FirstGeneral_Precision_Distribution82Analog 462 }
First_source_1_branch_63_output_power OBJECT-TYPE
	SYNTAX INTEGER
	UNITS     "0.01 "
	ACCESS read-only
	STATUS mandatory
	DESCRIPTION
		"First_source_1_branch_63_output_power"
	::= { FirstGeneral_Precision_Distribution82Analog 463 }
First_source_1_branch_64_output_power OBJECT-TYPE
	SYNTAX INTEGER
	UNITS     "0.01 "
	ACCESS read-only
	STATUS mandatory
	DESCRIPTION
		"First_source_1_branch_64_output_power"
	::= { FirstGeneral_Precision_Distribution82Analog 464 }
First_source_1_branch_65_output_power OBJECT-TYPE
	SYNTAX INTEGER
	UNITS     "0.01 "
	ACCESS read-only
	STATUS mandatory
	DESCRIPTION
		"First_source_1_branch_65_output_power"
	::= { FirstGeneral_Precision_Distribution82Analog 465 }
First_source_1_branch_66_output_power OBJECT-TYPE
	SYNTAX INTEGER
	UNITS     "0.01 "
	ACCESS read-only
	STATUS mandatory
	DESCRIPTION
		"First_source_1_branch_66_output_power"
	::= { FirstGeneral_Precision_Distribution82Analog 466 }
First_source_1_branch_67_output_power OBJECT-TYPE
	SYNTAX INTEGER
	UNITS     "0.01 "
	ACCESS read-only
	STATUS mandatory
	DESCRIPTION
		"First_source_1_branch_67_output_power"
	::= { FirstGeneral_Precision_Distribution82Analog 467 }
First_source_1_branch_68_output_power OBJECT-TYPE
	SYNTAX INTEGER
	UNITS     "0.01 "
	ACCESS read-only
	STATUS mandatory
	DESCRIPTION
		"First_source_1_branch_68_output_power"
	::= { FirstGeneral_Precision_Distribution82Analog 468 }
First_source_1_branch_69_output_power OBJECT-TYPE
	SYNTAX INTEGER
	UNITS     "0.01 "
	ACCESS read-only
	STATUS mandatory
	DESCRIPTION
		"First_source_1_branch_69_output_power"
	::= { FirstGeneral_Precision_Distribution82Analog 469 }
First_source_1_branch_70_output_power OBJECT-TYPE
	SYNTAX INTEGER
	UNITS     "0.01 "
	ACCESS read-only
	STATUS mandatory
	DESCRIPTION
		"First_source_1_branch_70_output_power"
	::= { FirstGeneral_Precision_Distribution82Analog 470 }
First_source_1_branch_71_output_power OBJECT-TYPE
	SYNTAX INTEGER
	UNITS     "0.01 "
	ACCESS read-only
	STATUS mandatory
	DESCRIPTION
		"First_source_1_branch_71_output_power"
	::= { FirstGeneral_Precision_Distribution82Analog 471 }
First_source_1_branch_72_output_power OBJECT-TYPE
	SYNTAX INTEGER
	UNITS     "0.01 "
	ACCESS read-only
	STATUS mandatory
	DESCRIPTION
		"First_source_1_branch_72_output_power"
	::= { FirstGeneral_Precision_Distribution82Analog 472 }
First_source_1_branch_73_output_power OBJECT-TYPE
	SYNTAX INTEGER
	UNITS     "0.01 "
	ACCESS read-only
	STATUS mandatory
	DESCRIPTION
		"First_source_1_branch_73_output_power"
	::= { FirstGeneral_Precision_Distribution82Analog 473 }
First_source_1_branch_74_output_power OBJECT-TYPE
	SYNTAX INTEGER
	UNITS     "0.01 "
	ACCESS read-only
	STATUS mandatory
	DESCRIPTION
		"First_source_1_branch_74_output_power"
	::= { FirstGeneral_Precision_Distribution82Analog 474 }
First_source_1_branch_75_output_power OBJECT-TYPE
	SYNTAX INTEGER
	UNITS     "0.01 "
	ACCESS read-only
	STATUS mandatory
	DESCRIPTION
		"First_source_1_branch_75_output_power"
	::= { FirstGeneral_Precision_Distribution82Analog 475 }
First_source_1_branch_76_output_power OBJECT-TYPE
	SYNTAX INTEGER
	UNITS     "0.01 "
	ACCESS read-only
	STATUS mandatory
	DESCRIPTION
		"First_source_1_branch_76_output_power"
	::= { FirstGeneral_Precision_Distribution82Analog 476 }
First_source_1_branch_77_output_power OBJECT-TYPE
	SYNTAX INTEGER
	UNITS     "0.01 "
	ACCESS read-only
	STATUS mandatory
	DESCRIPTION
		"First_source_1_branch_77_output_power"
	::= { FirstGeneral_Precision_Distribution82Analog 477 }
First_source_1_branch_78_output_power OBJECT-TYPE
	SYNTAX INTEGER
	UNITS     "0.01 "
	ACCESS read-only
	STATUS mandatory
	DESCRIPTION
		"First_source_1_branch_78_output_power"
	::= { FirstGeneral_Precision_Distribution82Analog 478 }
First_source_1_branch_79_output_power OBJECT-TYPE
	SYNTAX INTEGER
	UNITS     "0.01 "
	ACCESS read-only
	STATUS mandatory
	DESCRIPTION
		"First_source_1_branch_79_output_power"
	::= { FirstGeneral_Precision_Distribution82Analog 479 }
First_source_1_branch_80_output_power OBJECT-TYPE
	SYNTAX INTEGER
	UNITS     "0.01 "
	ACCESS read-only
	STATUS mandatory
	DESCRIPTION
		"First_source_1_branch_80_output_power"
	::= { FirstGeneral_Precision_Distribution82Analog 480 }
First_source_1_branch_81_output_power OBJECT-TYPE
	SYNTAX INTEGER
	UNITS     "0.01 "
	ACCESS read-only
	STATUS mandatory
	DESCRIPTION
		"First_source_1_branch_81_output_power"
	::= { FirstGeneral_Precision_Distribution82Analog 481 }
First_source_1_branch_82_output_power OBJECT-TYPE
	SYNTAX INTEGER
	UNITS     "0.01 "
	ACCESS read-only
	STATUS mandatory
	DESCRIPTION
		"First_source_1_branch_82_output_power"
	::= { FirstGeneral_Precision_Distribution82Analog 482 }
First_source_1_branch_83_output_power OBJECT-TYPE
	SYNTAX INTEGER
	UNITS     "0.01 "
	ACCESS read-only
	STATUS mandatory
	DESCRIPTION
		"First_source_1_branch_83_output_power"
	::= { FirstGeneral_Precision_Distribution82Analog 483 }
First_source_1_branch_84_output_power OBJECT-TYPE
	SYNTAX INTEGER
	UNITS     "0.01 "
	ACCESS read-only
	STATUS mandatory
	DESCRIPTION
		"First_source_1_branch_84_output_power"
	::= { FirstGeneral_Precision_Distribution82Analog 484 }
First_source_1_branch_85_output_power OBJECT-TYPE
	SYNTAX INTEGER
	UNITS     "0.01 "
	ACCESS read-only
	STATUS mandatory
	DESCRIPTION
		"First_source_1_branch_85_output_power"
	::= { FirstGeneral_Precision_Distribution82Analog 485 }
First_source_1_branch_86_output_power OBJECT-TYPE
	SYNTAX INTEGER
	UNITS     "0.01 "
	ACCESS read-only
	STATUS mandatory
	DESCRIPTION
		"First_source_1_branch_86_output_power"
	::= { FirstGeneral_Precision_Distribution82Analog 486 }
First_source_1_branch_87_output_power OBJECT-TYPE
	SYNTAX INTEGER
	UNITS     "0.01 "
	ACCESS read-only
	STATUS mandatory
	DESCRIPTION
		"First_source_1_branch_87_output_power"
	::= { FirstGeneral_Precision_Distribution82Analog 487 }
First_source_1_branch_88_output_power OBJECT-TYPE
	SYNTAX INTEGER
	UNITS     "0.01 "
	ACCESS read-only
	STATUS mandatory
	DESCRIPTION
		"First_source_1_branch_88_output_power"
	::= { FirstGeneral_Precision_Distribution82Analog 488 }
First_source_1_branch_89_output_power OBJECT-TYPE
	SYNTAX INTEGER
	UNITS     "0.01 "
	ACCESS read-only
	STATUS mandatory
	DESCRIPTION
		"First_source_1_branch_89_output_power"
	::= { FirstGeneral_Precision_Distribution82Analog 489 }
First_source_1_branch_90_output_power OBJECT-TYPE
	SYNTAX INTEGER
	UNITS     "0.01 "
	ACCESS read-only
	STATUS mandatory
	DESCRIPTION
		"First_source_1_branch_90_output_power"
	::= { FirstGeneral_Precision_Distribution82Analog 490 }
First_source_1_branch_91_output_power OBJECT-TYPE
	SYNTAX INTEGER
	UNITS     "0.01 "
	ACCESS read-only
	STATUS mandatory
	DESCRIPTION
		"First_source_1_branch_91_output_power"
	::= { FirstGeneral_Precision_Distribution82Analog 491 }
First_source_1_branch_92_output_power OBJECT-TYPE
	SYNTAX INTEGER
	UNITS     "0.01 "
	ACCESS read-only
	STATUS mandatory
	DESCRIPTION
		"First_source_1_branch_92_output_power"
	::= { FirstGeneral_Precision_Distribution82Analog 492 }
First_source_1_branch_93_output_power OBJECT-TYPE
	SYNTAX INTEGER
	UNITS     "0.01 "
	ACCESS read-only
	STATUS mandatory
	DESCRIPTION
		"First_source_1_branch_93_output_power"
	::= { FirstGeneral_Precision_Distribution82Analog 493 }
First_source_1_branch_94_output_power OBJECT-TYPE
	SYNTAX INTEGER
	UNITS     "0.01 "
	ACCESS read-only
	STATUS mandatory
	DESCRIPTION
		"First_source_1_branch_94_output_power"
	::= { FirstGeneral_Precision_Distribution82Analog 494 }
First_source_1_branch_95_output_power OBJECT-TYPE
	SYNTAX INTEGER
	UNITS     "0.01 "
	ACCESS read-only
	STATUS mandatory
	DESCRIPTION
		"First_source_1_branch_95_output_power"
	::= { FirstGeneral_Precision_Distribution82Analog 495 }
First_source_1_branch_96_output_power OBJECT-TYPE
	SYNTAX INTEGER
	UNITS     "0.01 "
	ACCESS read-only
	STATUS mandatory
	DESCRIPTION
		"First_source_1_branch_96_output_power"
	::= { FirstGeneral_Precision_Distribution82Analog 496 }
First_source_1_branch_97_output_power OBJECT-TYPE
	SYNTAX INTEGER
	UNITS     "0.01 "
	ACCESS read-only
	STATUS mandatory
	DESCRIPTION
		"First_source_1_branch_97_output_power"
	::= { FirstGeneral_Precision_Distribution82Analog 497 }
First_source_1_branch_98_output_power OBJECT-TYPE
	SYNTAX INTEGER
	UNITS     "0.01 "
	ACCESS read-only
	STATUS mandatory
	DESCRIPTION
		"First_source_1_branch_98_output_power"
	::= { FirstGeneral_Precision_Distribution82Analog 498 }
First_source_1_branch_99_output_power OBJECT-TYPE
	SYNTAX INTEGER
	UNITS     "0.01 "
	ACCESS read-only
	STATUS mandatory
	DESCRIPTION
		"First_source_1_branch_99_output_power"
	::= { FirstGeneral_Precision_Distribution82Analog 499 }
First_source_1_branch_100_output_power OBJECT-TYPE
	SYNTAX INTEGER
	UNITS     "0.01 "
	ACCESS read-only
	STATUS mandatory
	DESCRIPTION
		"First_source_1_branch_100_output_power"
	::= { FirstGeneral_Precision_Distribution82Analog 500 }
First_source_2_branch_1_output_voltage OBJECT-TYPE
	SYNTAX INTEGER
	UNITS     "0.01 "
	ACCESS read-only
	STATUS mandatory
	DESCRIPTION
		"First_source_2_branch_1_output_voltage"
	::= { FirstGeneral_Precision_Distribution82Analog 501 }
First_source_2_branch_2_output_voltage OBJECT-TYPE
	SYNTAX INTEGER
	UNITS     "0.01V "
	ACCESS read-only
	STATUS mandatory
	DESCRIPTION
		"First_source_2_branch_2_output_voltage"
	::= { FirstGeneral_Precision_Distribution82Analog 502 }
First_source_2_branch_3_output_voltage OBJECT-TYPE
	SYNTAX INTEGER
	UNITS     "0.01 "
	ACCESS read-only
	STATUS mandatory
	DESCRIPTION
		"First_source_2_branch_3_output_voltage"
	::= { FirstGeneral_Precision_Distribution82Analog 503 }
First_source_2_branch_4_output_voltage OBJECT-TYPE
	SYNTAX INTEGER
	UNITS     "0.01 "
	ACCESS read-only
	STATUS mandatory
	DESCRIPTION
		"First_source_2_branch_4_output_voltage"
	::= { FirstGeneral_Precision_Distribution82Analog 504 }
First_source_2_branch_5_output_voltage OBJECT-TYPE
	SYNTAX INTEGER
	UNITS     "0.01 "
	ACCESS read-only
	STATUS mandatory
	DESCRIPTION
		"First_source_2_branch_5_output_voltage"
	::= { FirstGeneral_Precision_Distribution82Analog 505 }
First_source_2_branch_6_output_voltage OBJECT-TYPE
	SYNTAX INTEGER
	UNITS     "0.01 "
	ACCESS read-only
	STATUS mandatory
	DESCRIPTION
		"First_source_2_branch_6_output_voltage"
	::= { FirstGeneral_Precision_Distribution82Analog 506 }
First_source_2_branch_7_output_voltage OBJECT-TYPE
	SYNTAX INTEGER
	UNITS     "0.01 "
	ACCESS read-only
	STATUS mandatory
	DESCRIPTION
		"First_source_2_branch_7_output_voltage"
	::= { FirstGeneral_Precision_Distribution82Analog 507 }
First_source_2_branch_8_output_voltage OBJECT-TYPE
	SYNTAX INTEGER
	UNITS     "0.01 "
	ACCESS read-only
	STATUS mandatory
	DESCRIPTION
		"First_source_2_branch_8_output_voltage"
	::= { FirstGeneral_Precision_Distribution82Analog 508 }
First_source_2_branch_9_output_voltage OBJECT-TYPE
	SYNTAX INTEGER
	UNITS     "0.01 "
	ACCESS read-only
	STATUS mandatory
	DESCRIPTION
		"First_source_2_branch_9_output_voltage"
	::= { FirstGeneral_Precision_Distribution82Analog 509 }
First_source_2_branch_10_output_voltage OBJECT-TYPE
	SYNTAX INTEGER
	UNITS     "0.01 "
	ACCESS read-only
	STATUS mandatory
	DESCRIPTION
		"First_source_2_branch_10_output_voltage"
	::= { FirstGeneral_Precision_Distribution82Analog 510 }
First_source_2_branch_11_output_voltage OBJECT-TYPE
	SYNTAX INTEGER
	UNITS     "0.01 "
	ACCESS read-only
	STATUS mandatory
	DESCRIPTION
		"First_source_2_branch_11_output_voltage"
	::= { FirstGeneral_Precision_Distribution82Analog 511 }
First_source_2_branch_12_output_voltage OBJECT-TYPE
	SYNTAX INTEGER
	UNITS     "0.01 "
	ACCESS read-only
	STATUS mandatory
	DESCRIPTION
		"First_source_2_branch_12_output_voltage"
	::= { FirstGeneral_Precision_Distribution82Analog 512 }
First_source_2_branch_13_output_voltage OBJECT-TYPE
	SYNTAX INTEGER
	UNITS     "0.01 "
	ACCESS read-only
	STATUS mandatory
	DESCRIPTION
		"First_source_2_branch_13_output_voltage"
	::= { FirstGeneral_Precision_Distribution82Analog 513 }
First_source_2_branch_14_output_voltage OBJECT-TYPE
	SYNTAX INTEGER
	UNITS     "0.01 "
	ACCESS read-only
	STATUS mandatory
	DESCRIPTION
		"First_source_2_branch_14_output_voltage"
	::= { FirstGeneral_Precision_Distribution82Analog 514 }
First_source_2_branch_15_output_voltage OBJECT-TYPE
	SYNTAX INTEGER
	UNITS     "0.01 "
	ACCESS read-only
	STATUS mandatory
	DESCRIPTION
		"First_source_2_branch_15_output_voltage"
	::= { FirstGeneral_Precision_Distribution82Analog 515 }
First_source_2_branch_16_output_voltage OBJECT-TYPE
	SYNTAX INTEGER
	UNITS     "0.01 "
	ACCESS read-only
	STATUS mandatory
	DESCRIPTION
		"First_source_2_branch_16_output_voltage"
	::= { FirstGeneral_Precision_Distribution82Analog 516 }
First_source_2_branch_17_output_voltage OBJECT-TYPE
	SYNTAX INTEGER
	UNITS     "0.01 "
	ACCESS read-only
	STATUS mandatory
	DESCRIPTION
		"First_source_2_branch_17_output_voltage"
	::= { FirstGeneral_Precision_Distribution82Analog 517 }
First_source_2_branch_18_output_voltage OBJECT-TYPE
	SYNTAX INTEGER
	UNITS     "0.01 "
	ACCESS read-only
	STATUS mandatory
	DESCRIPTION
		"First_source_2_branch_18_output_voltage"
	::= { FirstGeneral_Precision_Distribution82Analog 518 }
First_source_2_branch_19_output_voltage OBJECT-TYPE
	SYNTAX INTEGER
	UNITS     "0.01 "
	ACCESS read-only
	STATUS mandatory
	DESCRIPTION
		"First_source_2_branch_19_output_voltage"
	::= { FirstGeneral_Precision_Distribution82Analog 519 }
First_source_2_branch_20_output_voltage OBJECT-TYPE
	SYNTAX INTEGER
	UNITS     "0.01 "
	ACCESS read-only
	STATUS mandatory
	DESCRIPTION
		"First_source_2_branch_20_output_voltage"
	::= { FirstGeneral_Precision_Distribution82Analog 520 }
First_source_2_branch_21_output_voltage OBJECT-TYPE
	SYNTAX INTEGER
	UNITS     "0.01 "
	ACCESS read-only
	STATUS mandatory
	DESCRIPTION
		"First_source_2_branch_21_output_voltage"
	::= { FirstGeneral_Precision_Distribution82Analog 521 }
First_source_2_branch_22_output_voltage OBJECT-TYPE
	SYNTAX INTEGER
	UNITS     "0.01 "
	ACCESS read-only
	STATUS mandatory
	DESCRIPTION
		"First_source_2_branch_22_output_voltage"
	::= { FirstGeneral_Precision_Distribution82Analog 522 }
First_source_2_branch_23_output_voltage OBJECT-TYPE
	SYNTAX INTEGER
	UNITS     "0.01 "
	ACCESS read-only
	STATUS mandatory
	DESCRIPTION
		"First_source_2_branch_23_output_voltage"
	::= { FirstGeneral_Precision_Distribution82Analog 523 }
First_source_2_branch_24_output_voltage OBJECT-TYPE
	SYNTAX INTEGER
	UNITS     "0.01 "
	ACCESS read-only
	STATUS mandatory
	DESCRIPTION
		"First_source_2_branch_24_output_voltage"
	::= { FirstGeneral_Precision_Distribution82Analog 524 }
First_source_2_branch_25_output_voltage OBJECT-TYPE
	SYNTAX INTEGER
	UNITS     "0.01 "
	ACCESS read-only
	STATUS mandatory
	DESCRIPTION
		"First_source_2_branch_25_output_voltage"
	::= { FirstGeneral_Precision_Distribution82Analog 525 }
First_source_2_branch_26_output_voltage OBJECT-TYPE
	SYNTAX INTEGER
	UNITS     "0.01 "
	ACCESS read-only
	STATUS mandatory
	DESCRIPTION
		"First_source_2_branch_26_output_voltage"
	::= { FirstGeneral_Precision_Distribution82Analog 526 }
First_source_2_branch_27_output_voltage OBJECT-TYPE
	SYNTAX INTEGER
	UNITS     "0.01 "
	ACCESS read-only
	STATUS mandatory
	DESCRIPTION
		"First_source_2_branch_27_output_voltage"
	::= { FirstGeneral_Precision_Distribution82Analog 527 }
First_source_2_branch_28_output_voltage OBJECT-TYPE
	SYNTAX INTEGER
	UNITS     "0.01 "
	ACCESS read-only
	STATUS mandatory
	DESCRIPTION
		"First_source_2_branch_28_output_voltage"
	::= { FirstGeneral_Precision_Distribution82Analog 528 }
First_source_2_branch_29_output_voltage OBJECT-TYPE
	SYNTAX INTEGER
	UNITS     "0.01 "
	ACCESS read-only
	STATUS mandatory
	DESCRIPTION
		"First_source_2_branch_29_output_voltage"
	::= { FirstGeneral_Precision_Distribution82Analog 529 }
First_source_2_branch_30_output_voltage OBJECT-TYPE
	SYNTAX INTEGER
	UNITS     "0.01 "
	ACCESS read-only
	STATUS mandatory
	DESCRIPTION
		"First_source_2_branch_30_output_voltage"
	::= { FirstGeneral_Precision_Distribution82Analog 530 }
First_source_2_branch_31_output_voltage OBJECT-TYPE
	SYNTAX INTEGER
	UNITS     "0.01 "
	ACCESS read-only
	STATUS mandatory
	DESCRIPTION
		"First_source_2_branch_31_output_voltage"
	::= { FirstGeneral_Precision_Distribution82Analog 531 }
First_source_2_branch_32_output_voltage OBJECT-TYPE
	SYNTAX INTEGER
	UNITS     "0.01 "
	ACCESS read-only
	STATUS mandatory
	DESCRIPTION
		"First_source_2_branch_32_output_voltage"
	::= { FirstGeneral_Precision_Distribution82Analog 532 }
First_source_2_branch_33_output_voltage OBJECT-TYPE
	SYNTAX INTEGER
	UNITS     "0.01 "
	ACCESS read-only
	STATUS mandatory
	DESCRIPTION
		"First_source_2_branch_33_output_voltage"
	::= { FirstGeneral_Precision_Distribution82Analog 533 }
First_source_2_branch_34_output_voltage OBJECT-TYPE
	SYNTAX INTEGER
	UNITS     "0.01 "
	ACCESS read-only
	STATUS mandatory
	DESCRIPTION
		"First_source_2_branch_34_output_voltage"
	::= { FirstGeneral_Precision_Distribution82Analog 534 }
First_source_2_branch_35_output_voltage OBJECT-TYPE
	SYNTAX INTEGER
	UNITS     "0.01 "
	ACCESS read-only
	STATUS mandatory
	DESCRIPTION
		"First_source_2_branch_35_output_voltage"
	::= { FirstGeneral_Precision_Distribution82Analog 535 }
First_source_2_branch_36_output_voltage OBJECT-TYPE
	SYNTAX INTEGER
	UNITS     "0.01 "
	ACCESS read-only
	STATUS mandatory
	DESCRIPTION
		"First_source_2_branch_36_output_voltage"
	::= { FirstGeneral_Precision_Distribution82Analog 536 }
First_source_2_branch_37_output_voltage OBJECT-TYPE
	SYNTAX INTEGER
	UNITS     "0.01 "
	ACCESS read-only
	STATUS mandatory
	DESCRIPTION
		"First_source_2_branch_37_output_voltage"
	::= { FirstGeneral_Precision_Distribution82Analog 537 }
First_source_2_branch_38_output_voltage OBJECT-TYPE
	SYNTAX INTEGER
	UNITS     "0.01 "
	ACCESS read-only
	STATUS mandatory
	DESCRIPTION
		"First_source_2_branch_38_output_voltage"
	::= { FirstGeneral_Precision_Distribution82Analog 538 }
First_source_2_branch_39_output_voltage OBJECT-TYPE
	SYNTAX INTEGER
	UNITS     "0.01 "
	ACCESS read-only
	STATUS mandatory
	DESCRIPTION
		"First_source_2_branch_39_output_voltage"
	::= { FirstGeneral_Precision_Distribution82Analog 539 }
First_source_2_branch_40_output_voltage OBJECT-TYPE
	SYNTAX INTEGER
	UNITS     "0.01 "
	ACCESS read-only
	STATUS mandatory
	DESCRIPTION
		"First_source_2_branch_40_output_voltage"
	::= { FirstGeneral_Precision_Distribution82Analog 540 }
First_source_2_branch_41_output_voltage OBJECT-TYPE
	SYNTAX INTEGER
	UNITS     "0.01 "
	ACCESS read-only
	STATUS mandatory
	DESCRIPTION
		"First_source_2_branch_41_output_voltage"
	::= { FirstGeneral_Precision_Distribution82Analog 541 }
First_source_2_branch_42_output_voltage OBJECT-TYPE
	SYNTAX INTEGER
	UNITS     "0.01 "
	ACCESS read-only
	STATUS mandatory
	DESCRIPTION
		"First_source_2_branch_42_output_voltage"
	::= { FirstGeneral_Precision_Distribution82Analog 542 }
First_source_2_branch_43_output_voltage OBJECT-TYPE
	SYNTAX INTEGER
	UNITS     "0.01 "
	ACCESS read-only
	STATUS mandatory
	DESCRIPTION
		"First_source_2_branch_43_output_voltage"
	::= { FirstGeneral_Precision_Distribution82Analog 543 }
First_source_2_branch_44_output_voltage OBJECT-TYPE
	SYNTAX INTEGER
	UNITS     "0.01 "
	ACCESS read-only
	STATUS mandatory
	DESCRIPTION
		"First_source_2_branch_44_output_voltage"
	::= { FirstGeneral_Precision_Distribution82Analog 544 }
First_source_2_branch_45_output_voltage OBJECT-TYPE
	SYNTAX INTEGER
	UNITS     "0.01 "
	ACCESS read-only
	STATUS mandatory
	DESCRIPTION
		"First_source_2_branch_45_output_voltage"
	::= { FirstGeneral_Precision_Distribution82Analog 545 }
First_source_2_branch_46_output_voltage OBJECT-TYPE
	SYNTAX INTEGER
	UNITS     "0.01 "
	ACCESS read-only
	STATUS mandatory
	DESCRIPTION
		"First_source_2_branch_46_output_voltage"
	::= { FirstGeneral_Precision_Distribution82Analog 546 }
First_source_2_branch_47_output_voltage OBJECT-TYPE
	SYNTAX INTEGER
	UNITS     "0.01 "
	ACCESS read-only
	STATUS mandatory
	DESCRIPTION
		"First_source_2_branch_47_output_voltage"
	::= { FirstGeneral_Precision_Distribution82Analog 547 }
First_source_2_branch_48_output_voltage OBJECT-TYPE
	SYNTAX INTEGER
	UNITS     "0.01 "
	ACCESS read-only
	STATUS mandatory
	DESCRIPTION
		"First_source_2_branch_48_output_voltage"
	::= { FirstGeneral_Precision_Distribution82Analog 548 }
First_source_2_branch_49_output_voltage OBJECT-TYPE
	SYNTAX INTEGER
	UNITS     "0.01 "
	ACCESS read-only
	STATUS mandatory
	DESCRIPTION
		"First_source_2_branch_49_output_voltage"
	::= { FirstGeneral_Precision_Distribution82Analog 549 }
First_source_2_branch_50_output_voltage OBJECT-TYPE
	SYNTAX INTEGER
	UNITS     "0.01 "
	ACCESS read-only
	STATUS mandatory
	DESCRIPTION
		"First_source_2_branch_50_output_voltage"
	::= { FirstGeneral_Precision_Distribution82Analog 550 }
First_source_2_branch_51_output_voltage OBJECT-TYPE
	SYNTAX INTEGER
	UNITS     "0.01 "
	ACCESS read-only
	STATUS mandatory
	DESCRIPTION
		"First_source_2_branch_51_output_voltage"
	::= { FirstGeneral_Precision_Distribution82Analog 551 }
First_source_2_branch_52_output_voltage OBJECT-TYPE
	SYNTAX INTEGER
	UNITS     "0.01 "
	ACCESS read-only
	STATUS mandatory
	DESCRIPTION
		"First_source_2_branch_52_output_voltage"
	::= { FirstGeneral_Precision_Distribution82Analog 552 }
First_source_2_branch_53_output_voltage OBJECT-TYPE
	SYNTAX INTEGER
	UNITS     "0.01 "
	ACCESS read-only
	STATUS mandatory
	DESCRIPTION
		"First_source_2_branch_53_output_voltage"
	::= { FirstGeneral_Precision_Distribution82Analog 553 }
First_source_2_branch_54_output_voltage OBJECT-TYPE
	SYNTAX INTEGER
	UNITS     "0.01 "
	ACCESS read-only
	STATUS mandatory
	DESCRIPTION
		"First_source_2_branch_54_output_voltage"
	::= { FirstGeneral_Precision_Distribution82Analog 554 }
First_source_2_branch_55_output_voltage OBJECT-TYPE
	SYNTAX INTEGER
	UNITS     "0.01 "
	ACCESS read-only
	STATUS mandatory
	DESCRIPTION
		"First_source_2_branch_55_output_voltage"
	::= { FirstGeneral_Precision_Distribution82Analog 555 }
First_source_2_branch_56_output_voltage OBJECT-TYPE
	SYNTAX INTEGER
	UNITS     "0.01 "
	ACCESS read-only
	STATUS mandatory
	DESCRIPTION
		"First_source_2_branch_56_output_voltage"
	::= { FirstGeneral_Precision_Distribution82Analog 556 }
First_source_2_branch_57_output_voltage OBJECT-TYPE
	SYNTAX INTEGER
	UNITS     "0.01 "
	ACCESS read-only
	STATUS mandatory
	DESCRIPTION
		"First_source_2_branch_57_output_voltage"
	::= { FirstGeneral_Precision_Distribution82Analog 557 }
First_source_2_branch_58_output_voltage OBJECT-TYPE
	SYNTAX INTEGER
	UNITS     "0.01 "
	ACCESS read-only
	STATUS mandatory
	DESCRIPTION
		"First_source_2_branch_58_output_voltage"
	::= { FirstGeneral_Precision_Distribution82Analog 558 }
First_source_2_branch_59_output_voltage OBJECT-TYPE
	SYNTAX INTEGER
	UNITS     "0.01 "
	ACCESS read-only
	STATUS mandatory
	DESCRIPTION
		"First_source_2_branch_59_output_voltage"
	::= { FirstGeneral_Precision_Distribution82Analog 559 }
First_source_2_branch_60_output_voltage OBJECT-TYPE
	SYNTAX INTEGER
	UNITS     "0.01 "
	ACCESS read-only
	STATUS mandatory
	DESCRIPTION
		"First_source_2_branch_60_output_voltage"
	::= { FirstGeneral_Precision_Distribution82Analog 560 }
First_source_2_branch_61_output_voltage OBJECT-TYPE
	SYNTAX INTEGER
	UNITS     "0.01 "
	ACCESS read-only
	STATUS mandatory
	DESCRIPTION
		"First_source_2_branch_61_output_voltage"
	::= { FirstGeneral_Precision_Distribution82Analog 561 }
First_source_2_branch_62_output_voltage OBJECT-TYPE
	SYNTAX INTEGER
	UNITS     "0.01 "
	ACCESS read-only
	STATUS mandatory
	DESCRIPTION
		"First_source_2_branch_62_output_voltage"
	::= { FirstGeneral_Precision_Distribution82Analog 562 }
First_source_2_branch_63_output_voltage OBJECT-TYPE
	SYNTAX INTEGER
	UNITS     "0.01 "
	ACCESS read-only
	STATUS mandatory
	DESCRIPTION
		"First_source_2_branch_63_output_voltage"
	::= { FirstGeneral_Precision_Distribution82Analog 563 }
First_source_2_branch_64_output_voltage OBJECT-TYPE
	SYNTAX INTEGER
	UNITS     "0.01 "
	ACCESS read-only
	STATUS mandatory
	DESCRIPTION
		"First_source_2_branch_64_output_voltage"
	::= { FirstGeneral_Precision_Distribution82Analog 564 }
First_source_2_branch_65_output_voltage OBJECT-TYPE
	SYNTAX INTEGER
	UNITS     "0.01 "
	ACCESS read-only
	STATUS mandatory
	DESCRIPTION
		"First_source_2_branch_65_output_voltage"
	::= { FirstGeneral_Precision_Distribution82Analog 565 }
First_source_2_branch_66_output_voltage OBJECT-TYPE
	SYNTAX INTEGER
	UNITS     "0.01 "
	ACCESS read-only
	STATUS mandatory
	DESCRIPTION
		"First_source_2_branch_66_output_voltage"
	::= { FirstGeneral_Precision_Distribution82Analog 566 }
First_source_2_branch_67_output_voltage OBJECT-TYPE
	SYNTAX INTEGER
	UNITS     "0.01 "
	ACCESS read-only
	STATUS mandatory
	DESCRIPTION
		"First_source_2_branch_67_output_voltage"
	::= { FirstGeneral_Precision_Distribution82Analog 567 }
First_source_2_branch_68_output_voltage OBJECT-TYPE
	SYNTAX INTEGER
	UNITS     "0.01 "
	ACCESS read-only
	STATUS mandatory
	DESCRIPTION
		"First_source_2_branch_68_output_voltage"
	::= { FirstGeneral_Precision_Distribution82Analog 568 }
First_source_2_branch_69_output_voltage OBJECT-TYPE
	SYNTAX INTEGER
	UNITS     "0.01 "
	ACCESS read-only
	STATUS mandatory
	DESCRIPTION
		"First_source_2_branch_69_output_voltage"
	::= { FirstGeneral_Precision_Distribution82Analog 569 }
First_source_2_branch_70_output_voltage OBJECT-TYPE
	SYNTAX INTEGER
	UNITS     "0.01 "
	ACCESS read-only
	STATUS mandatory
	DESCRIPTION
		"First_source_2_branch_70_output_voltage"
	::= { FirstGeneral_Precision_Distribution82Analog 570 }
First_source_2_branch_71_output_voltage OBJECT-TYPE
	SYNTAX INTEGER
	UNITS     "0.01 "
	ACCESS read-only
	STATUS mandatory
	DESCRIPTION
		"First_source_2_branch_71_output_voltage"
	::= { FirstGeneral_Precision_Distribution82Analog 571 }
First_source_2_branch_72_output_voltage OBJECT-TYPE
	SYNTAX INTEGER
	UNITS     "0.01 "
	ACCESS read-only
	STATUS mandatory
	DESCRIPTION
		"First_source_2_branch_72_output_voltage"
	::= { FirstGeneral_Precision_Distribution82Analog 572 }
First_source_2_branch_73_output_voltage OBJECT-TYPE
	SYNTAX INTEGER
	UNITS     "0.01 "
	ACCESS read-only
	STATUS mandatory
	DESCRIPTION
		"First_source_2_branch_73_output_voltage"
	::= { FirstGeneral_Precision_Distribution82Analog 573 }
First_source_2_branch_74_output_voltage OBJECT-TYPE
	SYNTAX INTEGER
	UNITS     "0.01 "
	ACCESS read-only
	STATUS mandatory
	DESCRIPTION
		"First_source_2_branch_74_output_voltage"
	::= { FirstGeneral_Precision_Distribution82Analog 574 }
First_source_2_branch_75_output_voltage OBJECT-TYPE
	SYNTAX INTEGER
	UNITS     "0.01 "
	ACCESS read-only
	STATUS mandatory
	DESCRIPTION
		"First_source_2_branch_75_output_voltage"
	::= { FirstGeneral_Precision_Distribution82Analog 575 }
First_source_2_branch_76_output_voltage OBJECT-TYPE
	SYNTAX INTEGER
	UNITS     "0.01 "
	ACCESS read-only
	STATUS mandatory
	DESCRIPTION
		"First_source_2_branch_76_output_voltage"
	::= { FirstGeneral_Precision_Distribution82Analog 576 }
First_source_2_branch_77_output_voltage OBJECT-TYPE
	SYNTAX INTEGER
	UNITS     "0.01 "
	ACCESS read-only
	STATUS mandatory
	DESCRIPTION
		"First_source_2_branch_77_output_voltage"
	::= { FirstGeneral_Precision_Distribution82Analog 577 }
First_source_2_branch_78_output_voltage OBJECT-TYPE
	SYNTAX INTEGER
	UNITS     "0.01 "
	ACCESS read-only
	STATUS mandatory
	DESCRIPTION
		"First_source_2_branch_78_output_voltage"
	::= { FirstGeneral_Precision_Distribution82Analog 578 }
First_source_2_branch_79_output_voltage OBJECT-TYPE
	SYNTAX INTEGER
	UNITS     "0.01 "
	ACCESS read-only
	STATUS mandatory
	DESCRIPTION
		"First_source_2_branch_79_output_voltage"
	::= { FirstGeneral_Precision_Distribution82Analog 579 }
First_source_2_branch_80_output_voltage OBJECT-TYPE
	SYNTAX INTEGER
	UNITS     "0.01 "
	ACCESS read-only
	STATUS mandatory
	DESCRIPTION
		"First_source_2_branch_80_output_voltage"
	::= { FirstGeneral_Precision_Distribution82Analog 580 }
First_source_2_branch_81_output_voltage OBJECT-TYPE
	SYNTAX INTEGER
	UNITS     "0.01 "
	ACCESS read-only
	STATUS mandatory
	DESCRIPTION
		"First_source_2_branch_81_output_voltage"
	::= { FirstGeneral_Precision_Distribution82Analog 581 }
First_source_2_branch_82_output_voltage OBJECT-TYPE
	SYNTAX INTEGER
	UNITS     "0.01 "
	ACCESS read-only
	STATUS mandatory
	DESCRIPTION
		"First_source_2_branch_82_output_voltage"
	::= { FirstGeneral_Precision_Distribution82Analog 582 }
First_source_2_branch_83_output_voltage OBJECT-TYPE
	SYNTAX INTEGER
	UNITS     "0.01 "
	ACCESS read-only
	STATUS mandatory
	DESCRIPTION
		"First_source_2_branch_83_output_voltage"
	::= { FirstGeneral_Precision_Distribution82Analog 583 }
First_source_2_branch_84_output_voltage OBJECT-TYPE
	SYNTAX INTEGER
	UNITS     "0.01 "
	ACCESS read-only
	STATUS mandatory
	DESCRIPTION
		"First_source_2_branch_84_output_voltage"
	::= { FirstGeneral_Precision_Distribution82Analog 584 }
First_source_2_branch_85_output_voltage OBJECT-TYPE
	SYNTAX INTEGER
	UNITS     "0.01 "
	ACCESS read-only
	STATUS mandatory
	DESCRIPTION
		"First_source_2_branch_85_output_voltage"
	::= { FirstGeneral_Precision_Distribution82Analog 585 }
First_source_2_branch_86_output_voltage OBJECT-TYPE
	SYNTAX INTEGER
	UNITS     "0.01 "
	ACCESS read-only
	STATUS mandatory
	DESCRIPTION
		"First_source_2_branch_86_output_voltage"
	::= { FirstGeneral_Precision_Distribution82Analog 586 }
First_source_2_branch_87_output_voltage OBJECT-TYPE
	SYNTAX INTEGER
	UNITS     "0.01 "
	ACCESS read-only
	STATUS mandatory
	DESCRIPTION
		"First_source_2_branch_87_output_voltage"
	::= { FirstGeneral_Precision_Distribution82Analog 587 }
First_source_2_branch_88_output_voltage OBJECT-TYPE
	SYNTAX INTEGER
	UNITS     "0.01 "
	ACCESS read-only
	STATUS mandatory
	DESCRIPTION
		"First_source_2_branch_88_output_voltage"
	::= { FirstGeneral_Precision_Distribution82Analog 588 }
First_source_2_branch_89_output_voltage OBJECT-TYPE
	SYNTAX INTEGER
	UNITS     "0.01 "
	ACCESS read-only
	STATUS mandatory
	DESCRIPTION
		"First_source_2_branch_89_output_voltage"
	::= { FirstGeneral_Precision_Distribution82Analog 589 }
First_source_2_branch_90_output_voltage OBJECT-TYPE
	SYNTAX INTEGER
	UNITS     "0.01 "
	ACCESS read-only
	STATUS mandatory
	DESCRIPTION
		"First_source_2_branch_90_output_voltage"
	::= { FirstGeneral_Precision_Distribution82Analog 590 }
First_source_2_branch_91_output_voltage OBJECT-TYPE
	SYNTAX INTEGER
	UNITS     "0.01 "
	ACCESS read-only
	STATUS mandatory
	DESCRIPTION
		"First_source_2_branch_91_output_voltage"
	::= { FirstGeneral_Precision_Distribution82Analog 591 }
First_source_2_branch_92_output_voltage OBJECT-TYPE
	SYNTAX INTEGER
	UNITS     "0.01 "
	ACCESS read-only
	STATUS mandatory
	DESCRIPTION
		"First_source_2_branch_92_output_voltage"
	::= { FirstGeneral_Precision_Distribution82Analog 592 }
First_source_2_branch_93_output_voltage OBJECT-TYPE
	SYNTAX INTEGER
	UNITS     "0.01 "
	ACCESS read-only
	STATUS mandatory
	DESCRIPTION
		"First_source_2_branch_93_output_voltage"
	::= { FirstGeneral_Precision_Distribution82Analog 593 }
First_source_2_branch_94_output_voltage OBJECT-TYPE
	SYNTAX INTEGER
	UNITS     "0.01 "
	ACCESS read-only
	STATUS mandatory
	DESCRIPTION
		"First_source_2_branch_94_output_voltage"
	::= { FirstGeneral_Precision_Distribution82Analog 594 }
First_source_2_branch_95_output_voltage OBJECT-TYPE
	SYNTAX INTEGER
	UNITS     "0.01 "
	ACCESS read-only
	STATUS mandatory
	DESCRIPTION
		"First_source_2_branch_95_output_voltage"
	::= { FirstGeneral_Precision_Distribution82Analog 595 }
First_source_2_branch_96_output_voltage OBJECT-TYPE
	SYNTAX INTEGER
	UNITS     "0.01 "
	ACCESS read-only
	STATUS mandatory
	DESCRIPTION
		"First_source_2_branch_96_output_voltage"
	::= { FirstGeneral_Precision_Distribution82Analog 596 }
First_source_2_branch_97_output_voltage OBJECT-TYPE
	SYNTAX INTEGER
	UNITS     "0.01 "
	ACCESS read-only
	STATUS mandatory
	DESCRIPTION
		"First_source_2_branch_97_output_voltage"
	::= { FirstGeneral_Precision_Distribution82Analog 597 }
First_source_2_branch_98_output_voltage OBJECT-TYPE
	SYNTAX INTEGER
	UNITS     "0.01 "
	ACCESS read-only
	STATUS mandatory
	DESCRIPTION
		"First_source_2_branch_98_output_voltage"
	::= { FirstGeneral_Precision_Distribution82Analog 598 }
First_source_2_branch_99_output_voltage OBJECT-TYPE
	SYNTAX INTEGER
	UNITS     "0.01 "
	ACCESS read-only
	STATUS mandatory
	DESCRIPTION
		"First_source_2_branch_99_output_voltage"
	::= { FirstGeneral_Precision_Distribution82Analog 599 }
First_source_2_branch_100_output_voltage OBJECT-TYPE
	SYNTAX INTEGER
	UNITS     "0.01 "
	ACCESS read-only
	STATUS mandatory
	DESCRIPTION
		"First_source_2_branch_100_output_voltage"
	::= { FirstGeneral_Precision_Distribution82Analog 600 }
First_source_2_branch_1_output_Electric_Energy OBJECT-TYPE
	SYNTAX INTEGER
	UNITS     "0.01KWh "
	ACCESS read-only
	STATUS mandatory
	DESCRIPTION
		"First_source_2_branch_1_output_Electric_Energy"
	::= { FirstGeneral_Precision_Distribution82Analog 601 }
First_source_2_branch_2_output_Electric_Energy OBJECT-TYPE
	SYNTAX INTEGER
	UNITS     "0.01 "
	ACCESS read-only
	STATUS mandatory
	DESCRIPTION
		"First_source_2_branch_2_output_Electric_Energy"
	::= { FirstGeneral_Precision_Distribution82Analog 602 }
First_source_2_branch_3_output_Electric_Energy OBJECT-TYPE
	SYNTAX INTEGER
	UNITS     "0.01 "
	ACCESS read-only
	STATUS mandatory
	DESCRIPTION
		"First_source_2_branch_3_output_Electric_Energy"
	::= { FirstGeneral_Precision_Distribution82Analog 603 }
First_source_2_branch_4_output_Electric_Energy OBJECT-TYPE
	SYNTAX INTEGER
	UNITS     "0.01 "
	ACCESS read-only
	STATUS mandatory
	DESCRIPTION
		"First_source_2_branch_4_output_Electric_Energy"
	::= { FirstGeneral_Precision_Distribution82Analog 604 }
First_source_2_branch_5_output_Electric_Energy OBJECT-TYPE
	SYNTAX INTEGER
	UNITS     "0.01 "
	ACCESS read-only
	STATUS mandatory
	DESCRIPTION
		"First_source_2_branch_5_output_Electric_Energy"
	::= { FirstGeneral_Precision_Distribution82Analog 605 }
First_source_2_branch_6_output_Electric_Energy OBJECT-TYPE
	SYNTAX INTEGER
	UNITS     "0.01 "
	ACCESS read-only
	STATUS mandatory
	DESCRIPTION
		"First_source_2_branch_6_output_Electric_Energy"
	::= { FirstGeneral_Precision_Distribution82Analog 606 }
First_source_2_branch_7_output_Electric_Energy OBJECT-TYPE
	SYNTAX INTEGER
	UNITS     "0.01 "
	ACCESS read-only
	STATUS mandatory
	DESCRIPTION
		"First_source_2_branch_7_output_Electric_Energy"
	::= { FirstGeneral_Precision_Distribution82Analog 607 }
First_source_2_branch_8_output_Electric_Energy OBJECT-TYPE
	SYNTAX INTEGER
	UNITS     "0.01 "
	ACCESS read-only
	STATUS mandatory
	DESCRIPTION
		"First_source_2_branch_8_output_Electric_Energy"
	::= { FirstGeneral_Precision_Distribution82Analog 608 }
First_source_2_branch_9_output_Electric_Energy OBJECT-TYPE
	SYNTAX INTEGER
	UNITS     "0.01 "
	ACCESS read-only
	STATUS mandatory
	DESCRIPTION
		"First_source_2_branch_9_output_Electric_Energy"
	::= { FirstGeneral_Precision_Distribution82Analog 609 }
First_source_2_branch_10_output_Electric_Energy OBJECT-TYPE
	SYNTAX INTEGER
	UNITS     "0.01 "
	ACCESS read-only
	STATUS mandatory
	DESCRIPTION
		"First_source_2_branch_10_output_Electric_Energy"
	::= { FirstGeneral_Precision_Distribution82Analog 610 }
First_source_2_branch_11_output_Electric_Energy OBJECT-TYPE
	SYNTAX INTEGER
	UNITS     "0.01 "
	ACCESS read-only
	STATUS mandatory
	DESCRIPTION
		"First_source_2_branch_11_output_Electric_Energy"
	::= { FirstGeneral_Precision_Distribution82Analog 611 }
First_source_2_branch_12_output_Electric_Energy OBJECT-TYPE
	SYNTAX INTEGER
	UNITS     "0.01 "
	ACCESS read-only
	STATUS mandatory
	DESCRIPTION
		"First_source_2_branch_12_output_Electric_Energy"
	::= { FirstGeneral_Precision_Distribution82Analog 612 }
First_source_2_branch_13_output_Electric_Energy OBJECT-TYPE
	SYNTAX INTEGER
	UNITS     "0.01 "
	ACCESS read-only
	STATUS mandatory
	DESCRIPTION
		"First_source_2_branch_13_output_Electric_Energy"
	::= { FirstGeneral_Precision_Distribution82Analog 613 }
First_source_2_branch_14_output_Electric_Energy OBJECT-TYPE
	SYNTAX INTEGER
	UNITS     "0.01 "
	ACCESS read-only
	STATUS mandatory
	DESCRIPTION
		"First_source_2_branch_14_output_Electric_Energy"
	::= { FirstGeneral_Precision_Distribution82Analog 614 }
First_source_2_branch_15_output_Electric_Energy OBJECT-TYPE
	SYNTAX INTEGER
	UNITS     "0.01 "
	ACCESS read-only
	STATUS mandatory
	DESCRIPTION
		"First_source_2_branch_15_output_Electric_Energy"
	::= { FirstGeneral_Precision_Distribution82Analog 615 }
First_source_2_branch_16_output_Electric_Energy OBJECT-TYPE
	SYNTAX INTEGER
	UNITS     "0.01 "
	ACCESS read-only
	STATUS mandatory
	DESCRIPTION
		"First_source_2_branch_16_output_Electric_Energy"
	::= { FirstGeneral_Precision_Distribution82Analog 616 }
First_source_2_branch_17_output_Electric_Energy OBJECT-TYPE
	SYNTAX INTEGER
	UNITS     "0.01 "
	ACCESS read-only
	STATUS mandatory
	DESCRIPTION
		"First_source_2_branch_17_output_Electric_Energy"
	::= { FirstGeneral_Precision_Distribution82Analog 617 }
First_source_2_branch_18_output_Electric_Energy OBJECT-TYPE
	SYNTAX INTEGER
	UNITS     "0.01 "
	ACCESS read-only
	STATUS mandatory
	DESCRIPTION
		"First_source_2_branch_18_output_Electric_Energy"
	::= { FirstGeneral_Precision_Distribution82Analog 618 }
First_source_2_branch_19_output_Electric_Energy OBJECT-TYPE
	SYNTAX INTEGER
	UNITS     "0.01 "
	ACCESS read-only
	STATUS mandatory
	DESCRIPTION
		"First_source_2_branch_19_output_Electric_Energy"
	::= { FirstGeneral_Precision_Distribution82Analog 619 }
First_source_2_branch_20_output_Electric_Energy OBJECT-TYPE
	SYNTAX INTEGER
	UNITS     "0.01 "
	ACCESS read-only
	STATUS mandatory
	DESCRIPTION
		"First_source_2_branch_20_output_Electric_Energy"
	::= { FirstGeneral_Precision_Distribution82Analog 620 }
First_source_2_branch_21_output_Electric_Energy OBJECT-TYPE
	SYNTAX INTEGER
	UNITS     "0.01 "
	ACCESS read-only
	STATUS mandatory
	DESCRIPTION
		"First_source_2_branch_21_output_Electric_Energy"
	::= { FirstGeneral_Precision_Distribution82Analog 621 }
First_source_2_branch_22_output_Electric_Energy OBJECT-TYPE
	SYNTAX INTEGER
	UNITS     "0.01 "
	ACCESS read-only
	STATUS mandatory
	DESCRIPTION
		"First_source_2_branch_22_output_Electric_Energy"
	::= { FirstGeneral_Precision_Distribution82Analog 622 }
First_source_2_branch_23_output_Electric_Energy OBJECT-TYPE
	SYNTAX INTEGER
	UNITS     "0.01 "
	ACCESS read-only
	STATUS mandatory
	DESCRIPTION
		"First_source_2_branch_23_output_Electric_Energy"
	::= { FirstGeneral_Precision_Distribution82Analog 623 }
First_source_2_branch_24_output_Electric_Energy OBJECT-TYPE
	SYNTAX INTEGER
	UNITS     "0.01 "
	ACCESS read-only
	STATUS mandatory
	DESCRIPTION
		"First_source_2_branch_24_output_Electric_Energy"
	::= { FirstGeneral_Precision_Distribution82Analog 624 }
First_source_2_branch_25_output_Electric_Energy OBJECT-TYPE
	SYNTAX INTEGER
	UNITS     "0.01 "
	ACCESS read-only
	STATUS mandatory
	DESCRIPTION
		"First_source_2_branch_25_output_Electric_Energy"
	::= { FirstGeneral_Precision_Distribution82Analog 625 }
First_source_2_branch_26_output_Electric_Energy OBJECT-TYPE
	SYNTAX INTEGER
	UNITS     "0.01 "
	ACCESS read-only
	STATUS mandatory
	DESCRIPTION
		"First_source_2_branch_26_output_Electric_Energy"
	::= { FirstGeneral_Precision_Distribution82Analog 626 }
First_source_2_branch_27_output_Electric_Energy OBJECT-TYPE
	SYNTAX INTEGER
	UNITS     "0.01 "
	ACCESS read-only
	STATUS mandatory
	DESCRIPTION
		"First_source_2_branch_27_output_Electric_Energy"
	::= { FirstGeneral_Precision_Distribution82Analog 627 }
First_source_2_branch_28_output_Electric_Energy OBJECT-TYPE
	SYNTAX INTEGER
	UNITS     "0.01 "
	ACCESS read-only
	STATUS mandatory
	DESCRIPTION
		"First_source_2_branch_28_output_Electric_Energy"
	::= { FirstGeneral_Precision_Distribution82Analog 628 }
First_source_2_branch_29_output_Electric_Energy OBJECT-TYPE
	SYNTAX INTEGER
	UNITS     "0.01 "
	ACCESS read-only
	STATUS mandatory
	DESCRIPTION
		"First_source_2_branch_29_output_Electric_Energy"
	::= { FirstGeneral_Precision_Distribution82Analog 629 }
First_source_2_branch_30_output_Electric_Energy OBJECT-TYPE
	SYNTAX INTEGER
	UNITS     "0.01 "
	ACCESS read-only
	STATUS mandatory
	DESCRIPTION
		"First_source_2_branch_30_output_Electric_Energy"
	::= { FirstGeneral_Precision_Distribution82Analog 630 }
First_source_2_branch_31_output_Electric_Energy OBJECT-TYPE
	SYNTAX INTEGER
	UNITS     "0.01 "
	ACCESS read-only
	STATUS mandatory
	DESCRIPTION
		"First_source_2_branch_31_output_Electric_Energy"
	::= { FirstGeneral_Precision_Distribution82Analog 631 }
First_source_2_branch_32_output_Electric_Energy OBJECT-TYPE
	SYNTAX INTEGER
	UNITS     "0.01 "
	ACCESS read-only
	STATUS mandatory
	DESCRIPTION
		"First_source_2_branch_32_output_Electric_Energy"
	::= { FirstGeneral_Precision_Distribution82Analog 632 }
First_source_2_branch_33_output_Electric_Energy OBJECT-TYPE
	SYNTAX INTEGER
	UNITS     "0.01 "
	ACCESS read-only
	STATUS mandatory
	DESCRIPTION
		"First_source_2_branch_33_output_Electric_Energy"
	::= { FirstGeneral_Precision_Distribution82Analog 633 }
First_source_2_branch_34_output_Electric_Energy OBJECT-TYPE
	SYNTAX INTEGER
	UNITS     "0.01 "
	ACCESS read-only
	STATUS mandatory
	DESCRIPTION
		"First_source_2_branch_34_output_Electric_Energy"
	::= { FirstGeneral_Precision_Distribution82Analog 634 }
First_source_2_branch_35_output_Electric_Energy OBJECT-TYPE
	SYNTAX INTEGER
	UNITS     "0.01 "
	ACCESS read-only
	STATUS mandatory
	DESCRIPTION
		"First_source_2_branch_35_output_Electric_Energy"
	::= { FirstGeneral_Precision_Distribution82Analog 635 }
First_source_2_branch_36_output_Electric_Energy OBJECT-TYPE
	SYNTAX INTEGER
	UNITS     "0.01 "
	ACCESS read-only
	STATUS mandatory
	DESCRIPTION
		"First_source_2_branch_36_output_Electric_Energy"
	::= { FirstGeneral_Precision_Distribution82Analog 636 }
First_source_2_branch_37_output_Electric_Energy OBJECT-TYPE
	SYNTAX INTEGER
	UNITS     "0.01 "
	ACCESS read-only
	STATUS mandatory
	DESCRIPTION
		"First_source_2_branch_37_output_Electric_Energy"
	::= { FirstGeneral_Precision_Distribution82Analog 637 }
First_source_2_branch_38_output_Electric_Energy OBJECT-TYPE
	SYNTAX INTEGER
	UNITS     "0.01 "
	ACCESS read-only
	STATUS mandatory
	DESCRIPTION
		"First_source_2_branch_38_output_Electric_Energy"
	::= { FirstGeneral_Precision_Distribution82Analog 638 }
First_source_2_branch_39_output_Electric_Energy OBJECT-TYPE
	SYNTAX INTEGER
	UNITS     "0.01 "
	ACCESS read-only
	STATUS mandatory
	DESCRIPTION
		"First_source_2_branch_39_output_Electric_Energy"
	::= { FirstGeneral_Precision_Distribution82Analog 639 }
First_source_2_branch_40_output_Electric_Energy OBJECT-TYPE
	SYNTAX INTEGER
	UNITS     "0.01 "
	ACCESS read-only
	STATUS mandatory
	DESCRIPTION
		"First_source_2_branch_40_output_Electric_Energy"
	::= { FirstGeneral_Precision_Distribution82Analog 640 }
First_source_2_branch_41_output_Electric_Energy OBJECT-TYPE
	SYNTAX INTEGER
	UNITS     "0.01 "
	ACCESS read-only
	STATUS mandatory
	DESCRIPTION
		"First_source_2_branch_41_output_Electric_Energy"
	::= { FirstGeneral_Precision_Distribution82Analog 641 }
First_source_2_branch_42_output_Electric_Energy OBJECT-TYPE
	SYNTAX INTEGER
	UNITS     "0.01 "
	ACCESS read-only
	STATUS mandatory
	DESCRIPTION
		"First_source_2_branch_42_output_Electric_Energy"
	::= { FirstGeneral_Precision_Distribution82Analog 642 }
First_source_2_branch_43_output_Electric_Energy OBJECT-TYPE
	SYNTAX INTEGER
	UNITS     "0.01 "
	ACCESS read-only
	STATUS mandatory
	DESCRIPTION
		"First_source_2_branch_43_output_Electric_Energy"
	::= { FirstGeneral_Precision_Distribution82Analog 643 }
First_source_2_branch_44_output_Electric_Energy OBJECT-TYPE
	SYNTAX INTEGER
	UNITS     "0.01 "
	ACCESS read-only
	STATUS mandatory
	DESCRIPTION
		"First_source_2_branch_44_output_Electric_Energy"
	::= { FirstGeneral_Precision_Distribution82Analog 644 }
First_source_2_branch_45_output_Electric_Energy OBJECT-TYPE
	SYNTAX INTEGER
	UNITS     "0.01 "
	ACCESS read-only
	STATUS mandatory
	DESCRIPTION
		"First_source_2_branch_45_output_Electric_Energy"
	::= { FirstGeneral_Precision_Distribution82Analog 645 }
First_source_2_branch_46_output_Electric_Energy OBJECT-TYPE
	SYNTAX INTEGER
	UNITS     "0.01 "
	ACCESS read-only
	STATUS mandatory
	DESCRIPTION
		"First_source_2_branch_46_output_Electric_Energy"
	::= { FirstGeneral_Precision_Distribution82Analog 646 }
First_source_2_branch_47_output_Electric_Energy OBJECT-TYPE
	SYNTAX INTEGER
	UNITS     "0.01 "
	ACCESS read-only
	STATUS mandatory
	DESCRIPTION
		"First_source_2_branch_47_output_Electric_Energy"
	::= { FirstGeneral_Precision_Distribution82Analog 647 }
First_source_2_branch_48_output_Electric_Energy OBJECT-TYPE
	SYNTAX INTEGER
	UNITS     "0.01 "
	ACCESS read-only
	STATUS mandatory
	DESCRIPTION
		"First_source_2_branch_48_output_Electric_Energy"
	::= { FirstGeneral_Precision_Distribution82Analog 648 }
First_source_2_branch_49_output_Electric_Energy OBJECT-TYPE
	SYNTAX INTEGER
	UNITS     "0.01 "
	ACCESS read-only
	STATUS mandatory
	DESCRIPTION
		"First_source_2_branch_49_output_Electric_Energy"
	::= { FirstGeneral_Precision_Distribution82Analog 649 }
First_source_2_branch_50_output_Electric_Energy OBJECT-TYPE
	SYNTAX INTEGER
	UNITS     "0.01 "
	ACCESS read-only
	STATUS mandatory
	DESCRIPTION
		"First_source_2_branch_50_output_Electric_Energy"
	::= { FirstGeneral_Precision_Distribution82Analog 650 }
First_source_2_branch_51_output_Electric_Energy OBJECT-TYPE
	SYNTAX INTEGER
	UNITS     "0.01 "
	ACCESS read-only
	STATUS mandatory
	DESCRIPTION
		"First_source_2_branch_51_output_Electric_Energy"
	::= { FirstGeneral_Precision_Distribution82Analog 651 }
First_source_2_branch_52_output_Electric_Energy OBJECT-TYPE
	SYNTAX INTEGER
	UNITS     "0.01 "
	ACCESS read-only
	STATUS mandatory
	DESCRIPTION
		"First_source_2_branch_52_output_Electric_Energy"
	::= { FirstGeneral_Precision_Distribution82Analog 652 }
First_source_2_branch_53_output_Electric_Energy OBJECT-TYPE
	SYNTAX INTEGER
	UNITS     "0.01 "
	ACCESS read-only
	STATUS mandatory
	DESCRIPTION
		"First_source_2_branch_53_output_Electric_Energy"
	::= { FirstGeneral_Precision_Distribution82Analog 653 }
First_source_2_branch_54_output_Electric_Energy OBJECT-TYPE
	SYNTAX INTEGER
	UNITS     "0.01 "
	ACCESS read-only
	STATUS mandatory
	DESCRIPTION
		"First_source_2_branch_54_output_Electric_Energy"
	::= { FirstGeneral_Precision_Distribution82Analog 654 }
First_source_2_branch_55_output_Electric_Energy OBJECT-TYPE
	SYNTAX INTEGER
	UNITS     "0.01 "
	ACCESS read-only
	STATUS mandatory
	DESCRIPTION
		"First_source_2_branch_55_output_Electric_Energy"
	::= { FirstGeneral_Precision_Distribution82Analog 655 }
First_source_2_branch_56_output_Electric_Energy OBJECT-TYPE
	SYNTAX INTEGER
	UNITS     "0.01 "
	ACCESS read-only
	STATUS mandatory
	DESCRIPTION
		"First_source_2_branch_56_output_Electric_Energy"
	::= { FirstGeneral_Precision_Distribution82Analog 656 }
First_source_2_branch_57_output_Electric_Energy OBJECT-TYPE
	SYNTAX INTEGER
	UNITS     "0.01 "
	ACCESS read-only
	STATUS mandatory
	DESCRIPTION
		"First_source_2_branch_57_output_Electric_Energy"
	::= { FirstGeneral_Precision_Distribution82Analog 657 }
First_source_2_branch_58_output_Electric_Energy OBJECT-TYPE
	SYNTAX INTEGER
	UNITS     "0.01 "
	ACCESS read-only
	STATUS mandatory
	DESCRIPTION
		"First_source_2_branch_58_output_Electric_Energy"
	::= { FirstGeneral_Precision_Distribution82Analog 658 }
First_source_2_branch_59_output_Electric_Energy OBJECT-TYPE
	SYNTAX INTEGER
	UNITS     "0.01 "
	ACCESS read-only
	STATUS mandatory
	DESCRIPTION
		"First_source_2_branch_59_output_Electric_Energy"
	::= { FirstGeneral_Precision_Distribution82Analog 659 }
First_source_2_branch_60_output_Electric_Energy OBJECT-TYPE
	SYNTAX INTEGER
	UNITS     "0.01 "
	ACCESS read-only
	STATUS mandatory
	DESCRIPTION
		"First_source_2_branch_60_output_Electric_Energy"
	::= { FirstGeneral_Precision_Distribution82Analog 660 }
First_source_2_branch_61_output_Electric_Energy OBJECT-TYPE
	SYNTAX INTEGER
	UNITS     "0.01 "
	ACCESS read-only
	STATUS mandatory
	DESCRIPTION
		"First_source_2_branch_61_output_Electric_Energy"
	::= { FirstGeneral_Precision_Distribution82Analog 661 }
First_source_2_branch_62_output_Electric_Energy OBJECT-TYPE
	SYNTAX INTEGER
	UNITS     "0.01 "
	ACCESS read-only
	STATUS mandatory
	DESCRIPTION
		"First_source_2_branch_62_output_Electric_Energy"
	::= { FirstGeneral_Precision_Distribution82Analog 662 }
First_source_2_branch_63_output_Electric_Energy OBJECT-TYPE
	SYNTAX INTEGER
	UNITS     "0.01 "
	ACCESS read-only
	STATUS mandatory
	DESCRIPTION
		"First_source_2_branch_63_output_Electric_Energy"
	::= { FirstGeneral_Precision_Distribution82Analog 663 }
First_source_2_branch_64_output_Electric_Energy OBJECT-TYPE
	SYNTAX INTEGER
	UNITS     "0.01 "
	ACCESS read-only
	STATUS mandatory
	DESCRIPTION
		"First_source_2_branch_64_output_Electric_Energy"
	::= { FirstGeneral_Precision_Distribution82Analog 664 }
First_source_2_branch_65_output_Electric_Energy OBJECT-TYPE
	SYNTAX INTEGER
	UNITS     "0.01 "
	ACCESS read-only
	STATUS mandatory
	DESCRIPTION
		"First_source_2_branch_65_output_Electric_Energy"
	::= { FirstGeneral_Precision_Distribution82Analog 665 }
First_source_2_branch_66_output_Electric_Energy OBJECT-TYPE
	SYNTAX INTEGER
	UNITS     "0.01 "
	ACCESS read-only
	STATUS mandatory
	DESCRIPTION
		"First_source_2_branch_66_output_Electric_Energy"
	::= { FirstGeneral_Precision_Distribution82Analog 666 }
First_source_2_branch_67_output_Electric_Energy OBJECT-TYPE
	SYNTAX INTEGER
	UNITS     "0.01 "
	ACCESS read-only
	STATUS mandatory
	DESCRIPTION
		"First_source_2_branch_67_output_Electric_Energy"
	::= { FirstGeneral_Precision_Distribution82Analog 667 }
First_source_2_branch_68_output_Electric_Energy OBJECT-TYPE
	SYNTAX INTEGER
	UNITS     "0.01 "
	ACCESS read-only
	STATUS mandatory
	DESCRIPTION
		"First_source_2_branch_68_output_Electric_Energy"
	::= { FirstGeneral_Precision_Distribution82Analog 668 }
First_source_2_branch_69_output_Electric_Energy OBJECT-TYPE
	SYNTAX INTEGER
	UNITS     "0.01 "
	ACCESS read-only
	STATUS mandatory
	DESCRIPTION
		"First_source_2_branch_69_output_Electric_Energy"
	::= { FirstGeneral_Precision_Distribution82Analog 669 }
First_source_2_branch_70_output_Electric_Energy OBJECT-TYPE
	SYNTAX INTEGER
	UNITS     "0.01 "
	ACCESS read-only
	STATUS mandatory
	DESCRIPTION
		"First_source_2_branch_70_output_Electric_Energy"
	::= { FirstGeneral_Precision_Distribution82Analog 670 }
First_source_2_branch_71_output_Electric_Energy OBJECT-TYPE
	SYNTAX INTEGER
	UNITS     "0.01 "
	ACCESS read-only
	STATUS mandatory
	DESCRIPTION
		"First_source_2_branch_71_output_Electric_Energy"
	::= { FirstGeneral_Precision_Distribution82Analog 671 }
First_source_2_branch_72_output_Electric_Energy OBJECT-TYPE
	SYNTAX INTEGER
	UNITS     "0.01 "
	ACCESS read-only
	STATUS mandatory
	DESCRIPTION
		"First_source_2_branch_72_output_Electric_Energy"
	::= { FirstGeneral_Precision_Distribution82Analog 672 }
First_source_2_branch_73_output_Electric_Energy OBJECT-TYPE
	SYNTAX INTEGER
	UNITS     "0.01 "
	ACCESS read-only
	STATUS mandatory
	DESCRIPTION
		"First_source_2_branch_73_output_Electric_Energy"
	::= { FirstGeneral_Precision_Distribution82Analog 673 }
First_source_2_branch_74_output_Electric_Energy OBJECT-TYPE
	SYNTAX INTEGER
	UNITS     "0.01 "
	ACCESS read-only
	STATUS mandatory
	DESCRIPTION
		"First_source_2_branch_74_output_Electric_Energy"
	::= { FirstGeneral_Precision_Distribution82Analog 674 }
First_source_2_branch_75_output_Electric_Energy OBJECT-TYPE
	SYNTAX INTEGER
	UNITS     "0.01 "
	ACCESS read-only
	STATUS mandatory
	DESCRIPTION
		"First_source_2_branch_75_output_Electric_Energy"
	::= { FirstGeneral_Precision_Distribution82Analog 675 }
First_source_2_branch_76_output_Electric_Energy OBJECT-TYPE
	SYNTAX INTEGER
	UNITS     "0.01 "
	ACCESS read-only
	STATUS mandatory
	DESCRIPTION
		"First_source_2_branch_76_output_Electric_Energy"
	::= { FirstGeneral_Precision_Distribution82Analog 676 }
First_source_2_branch_77_output_Electric_Energy OBJECT-TYPE
	SYNTAX INTEGER
	UNITS     "0.01 "
	ACCESS read-only
	STATUS mandatory
	DESCRIPTION
		"First_source_2_branch_77_output_Electric_Energy"
	::= { FirstGeneral_Precision_Distribution82Analog 677 }
First_source_2_branch_78_output_Electric_Energy OBJECT-TYPE
	SYNTAX INTEGER
	UNITS     "0.01 "
	ACCESS read-only
	STATUS mandatory
	DESCRIPTION
		"First_source_2_branch_78_output_Electric_Energy"
	::= { FirstGeneral_Precision_Distribution82Analog 678 }
First_source_2_branch_79_output_Electric_Energy OBJECT-TYPE
	SYNTAX INTEGER
	UNITS     "0.01 "
	ACCESS read-only
	STATUS mandatory
	DESCRIPTION
		"First_source_2_branch_79_output_Electric_Energy"
	::= { FirstGeneral_Precision_Distribution82Analog 679 }
First_source_2_branch_80_output_Electric_Energy OBJECT-TYPE
	SYNTAX INTEGER
	UNITS     "0.01 "
	ACCESS read-only
	STATUS mandatory
	DESCRIPTION
		"First_source_2_branch_80_output_Electric_Energy"
	::= { FirstGeneral_Precision_Distribution82Analog 680 }
First_source_2_branch_81_output_Electric_Energy OBJECT-TYPE
	SYNTAX INTEGER
	UNITS     "0.01 "
	ACCESS read-only
	STATUS mandatory
	DESCRIPTION
		"First_source_2_branch_81_output_Electric_Energy"
	::= { FirstGeneral_Precision_Distribution82Analog 681 }
First_source_2_branch_82_output_Electric_Energy OBJECT-TYPE
	SYNTAX INTEGER
	UNITS     "0.01 "
	ACCESS read-only
	STATUS mandatory
	DESCRIPTION
		"First_source_2_branch_82_output_Electric_Energy"
	::= { FirstGeneral_Precision_Distribution82Analog 682 }
First_source_2_branch_83_output_Electric_Energy OBJECT-TYPE
	SYNTAX INTEGER
	UNITS     "0.01 "
	ACCESS read-only
	STATUS mandatory
	DESCRIPTION
		"First_source_2_branch_83_output_Electric_Energy"
	::= { FirstGeneral_Precision_Distribution82Analog 683 }
First_source_2_branch_84_output_Electric_Energy OBJECT-TYPE
	SYNTAX INTEGER
	UNITS     "0.01 "
	ACCESS read-only
	STATUS mandatory
	DESCRIPTION
		"First_source_2_branch_84_output_Electric_Energy"
	::= { FirstGeneral_Precision_Distribution82Analog 684 }
First_source_2_branch_85_output_Electric_Energy OBJECT-TYPE
	SYNTAX INTEGER
	UNITS     "0.01 "
	ACCESS read-only
	STATUS mandatory
	DESCRIPTION
		"First_source_2_branch_85_output_Electric_Energy"
	::= { FirstGeneral_Precision_Distribution82Analog 685 }
First_source_2_branch_86_output_Electric_Energy OBJECT-TYPE
	SYNTAX INTEGER
	UNITS     "0.01 "
	ACCESS read-only
	STATUS mandatory
	DESCRIPTION
		"First_source_2_branch_86_output_Electric_Energy"
	::= { FirstGeneral_Precision_Distribution82Analog 686 }
First_source_2_branch_87_output_Electric_Energy OBJECT-TYPE
	SYNTAX INTEGER
	UNITS     "0.01 "
	ACCESS read-only
	STATUS mandatory
	DESCRIPTION
		"First_source_2_branch_87_output_Electric_Energy"
	::= { FirstGeneral_Precision_Distribution82Analog 687 }
First_source_2_branch_88_output_Electric_Energy OBJECT-TYPE
	SYNTAX INTEGER
	UNITS     "0.01 "
	ACCESS read-only
	STATUS mandatory
	DESCRIPTION
		"First_source_2_branch_88_output_Electric_Energy"
	::= { FirstGeneral_Precision_Distribution82Analog 688 }
First_source_2_branch_89_output_Electric_Energy OBJECT-TYPE
	SYNTAX INTEGER
	UNITS     "0.01 "
	ACCESS read-only
	STATUS mandatory
	DESCRIPTION
		"First_source_2_branch_89_output_Electric_Energy"
	::= { FirstGeneral_Precision_Distribution82Analog 689 }
First_source_2_branch_90_output_Electric_Energy OBJECT-TYPE
	SYNTAX INTEGER
	UNITS     "0.01 "
	ACCESS read-only
	STATUS mandatory
	DESCRIPTION
		"First_source_2_branch_90_output_Electric_Energy"
	::= { FirstGeneral_Precision_Distribution82Analog 690 }
First_source_2_branch_91_output_Electric_Energy OBJECT-TYPE
	SYNTAX INTEGER
	UNITS     "0.01 "
	ACCESS read-only
	STATUS mandatory
	DESCRIPTION
		"First_source_2_branch_91_output_Electric_Energy"
	::= { FirstGeneral_Precision_Distribution82Analog 691 }
First_source_2_branch_92_output_Electric_Energy OBJECT-TYPE
	SYNTAX INTEGER
	UNITS     "0.01 "
	ACCESS read-only
	STATUS mandatory
	DESCRIPTION
		"First_source_2_branch_92_output_Electric_Energy"
	::= { FirstGeneral_Precision_Distribution82Analog 692 }
First_source_2_branch_93_output_Electric_Energy OBJECT-TYPE
	SYNTAX INTEGER
	UNITS     "0.01 "
	ACCESS read-only
	STATUS mandatory
	DESCRIPTION
		"First_source_2_branch_93_output_Electric_Energy"
	::= { FirstGeneral_Precision_Distribution82Analog 693 }
First_source_2_branch_94_output_Electric_Energy OBJECT-TYPE
	SYNTAX INTEGER
	UNITS     "0.01 "
	ACCESS read-only
	STATUS mandatory
	DESCRIPTION
		"First_source_2_branch_94_output_Electric_Energy"
	::= { FirstGeneral_Precision_Distribution82Analog 694 }
First_source_2_branch_95_output_Electric_Energy OBJECT-TYPE
	SYNTAX INTEGER
	UNITS     "0.01 "
	ACCESS read-only
	STATUS mandatory
	DESCRIPTION
		"First_source_2_branch_95_output_Electric_Energy"
	::= { FirstGeneral_Precision_Distribution82Analog 695 }
First_source_2_branch_96_output_Electric_Energy OBJECT-TYPE
	SYNTAX INTEGER
	UNITS     "0.01 "
	ACCESS read-only
	STATUS mandatory
	DESCRIPTION
		"First_source_2_branch_96_output_Electric_Energy"
	::= { FirstGeneral_Precision_Distribution82Analog 696 }
First_source_2_branch_97_output_Electric_Energy OBJECT-TYPE
	SYNTAX INTEGER
	UNITS     "0.01 "
	ACCESS read-only
	STATUS mandatory
	DESCRIPTION
		"First_source_2_branch_97_output_Electric_Energy"
	::= { FirstGeneral_Precision_Distribution82Analog 697 }
First_source_2_branch_98_output_Electric_Energy OBJECT-TYPE
	SYNTAX INTEGER
	UNITS     "0.01 "
	ACCESS read-only
	STATUS mandatory
	DESCRIPTION
		"First_source_2_branch_98_output_Electric_Energy"
	::= { FirstGeneral_Precision_Distribution82Analog 698 }
First_source_2_branch_99_output_Electric_Energy OBJECT-TYPE
	SYNTAX INTEGER
	UNITS     "0.01 "
	ACCESS read-only
	STATUS mandatory
	DESCRIPTION
		"First_source_2_branch_99_output_Electric_Energy"
	::= { FirstGeneral_Precision_Distribution82Analog 699 }
First_source_2_branch_100_output_Electric_Energy OBJECT-TYPE
	SYNTAX INTEGER
	UNITS     "0.01 "
	ACCESS read-only
	STATUS mandatory
	DESCRIPTION
		"First_source_2_branch_100_output_Electric_Energy"
	::= { FirstGeneral_Precision_Distribution82Analog 700 }
First_source_2_branch_1_output_current OBJECT-TYPE
	SYNTAX INTEGER
	UNITS     "0.01A "
	ACCESS read-only
	STATUS mandatory
	DESCRIPTION
		"First_source_2_branch_1_output_current"
	::= { FirstGeneral_Precision_Distribution82Analog 701 }
First_source_2_branch_2_output_current OBJECT-TYPE
	SYNTAX INTEGER
	UNITS     "0.01 "
	ACCESS read-only
	STATUS mandatory
	DESCRIPTION
		"First_source_2_branch_2_output_current"
	::= { FirstGeneral_Precision_Distribution82Analog 702 }
First_source_2_branch_3_output_current OBJECT-TYPE
	SYNTAX INTEGER
	UNITS     "0.01 "
	ACCESS read-only
	STATUS mandatory
	DESCRIPTION
		"First_source_2_branch_3_output_current"
	::= { FirstGeneral_Precision_Distribution82Analog 703 }
First_source_2_branch_4_output_current OBJECT-TYPE
	SYNTAX INTEGER
	UNITS     "0.01 "
	ACCESS read-only
	STATUS mandatory
	DESCRIPTION
		"First_source_2_branch_4_output_current"
	::= { FirstGeneral_Precision_Distribution82Analog 704 }
First_source_2_branch_5_output_current OBJECT-TYPE
	SYNTAX INTEGER
	UNITS     "0.01 "
	ACCESS read-only
	STATUS mandatory
	DESCRIPTION
		"First_source_2_branch_5_output_current"
	::= { FirstGeneral_Precision_Distribution82Analog 705 }
First_source_2_branch_6_output_current OBJECT-TYPE
	SYNTAX INTEGER
	UNITS     "0.01 "
	ACCESS read-only
	STATUS mandatory
	DESCRIPTION
		"First_source_2_branch_6_output_current"
	::= { FirstGeneral_Precision_Distribution82Analog 706 }
First_source_2_branch_7_output_current OBJECT-TYPE
	SYNTAX INTEGER
	UNITS     "0.01 "
	ACCESS read-only
	STATUS mandatory
	DESCRIPTION
		"First_source_2_branch_7_output_current"
	::= { FirstGeneral_Precision_Distribution82Analog 707 }
First_source_2_branch_8_output_current OBJECT-TYPE
	SYNTAX INTEGER
	UNITS     "0.01 "
	ACCESS read-only
	STATUS mandatory
	DESCRIPTION
		"First_source_2_branch_8_output_current"
	::= { FirstGeneral_Precision_Distribution82Analog 708 }
First_source_2_branch_9_output_current OBJECT-TYPE
	SYNTAX INTEGER
	UNITS     "0.01 "
	ACCESS read-only
	STATUS mandatory
	DESCRIPTION
		"First_source_2_branch_9_output_current"
	::= { FirstGeneral_Precision_Distribution82Analog 709 }
First_source_2_branch_10_output_current OBJECT-TYPE
	SYNTAX INTEGER
	UNITS     "0.01 "
	ACCESS read-only
	STATUS mandatory
	DESCRIPTION
		"First_source_2_branch_10_output_current"
	::= { FirstGeneral_Precision_Distribution82Analog 710 }
First_source_2_branch_11_output_current OBJECT-TYPE
	SYNTAX INTEGER
	UNITS     "0.01 "
	ACCESS read-only
	STATUS mandatory
	DESCRIPTION
		"First_source_2_branch_11_output_current"
	::= { FirstGeneral_Precision_Distribution82Analog 711 }
First_source_2_branch_12_output_current OBJECT-TYPE
	SYNTAX INTEGER
	UNITS     "0.01 "
	ACCESS read-only
	STATUS mandatory
	DESCRIPTION
		"First_source_2_branch_12_output_current"
	::= { FirstGeneral_Precision_Distribution82Analog 712 }
First_source_2_branch_13_output_current OBJECT-TYPE
	SYNTAX INTEGER
	UNITS     "0.01 "
	ACCESS read-only
	STATUS mandatory
	DESCRIPTION
		"First_source_2_branch_13_output_current"
	::= { FirstGeneral_Precision_Distribution82Analog 713 }
First_source_2_branch_14_output_current OBJECT-TYPE
	SYNTAX INTEGER
	UNITS     "0.01 "
	ACCESS read-only
	STATUS mandatory
	DESCRIPTION
		"First_source_2_branch_14_output_current"
	::= { FirstGeneral_Precision_Distribution82Analog 714 }
First_source_2_branch_15_output_current OBJECT-TYPE
	SYNTAX INTEGER
	UNITS     "0.01 "
	ACCESS read-only
	STATUS mandatory
	DESCRIPTION
		"First_source_2_branch_15_output_current"
	::= { FirstGeneral_Precision_Distribution82Analog 715 }
First_source_2_branch_16_output_current OBJECT-TYPE
	SYNTAX INTEGER
	UNITS     "0.01 "
	ACCESS read-only
	STATUS mandatory
	DESCRIPTION
		"First_source_2_branch_16_output_current"
	::= { FirstGeneral_Precision_Distribution82Analog 716 }
First_source_2_branch_17_output_current OBJECT-TYPE
	SYNTAX INTEGER
	UNITS     "0.01 "
	ACCESS read-only
	STATUS mandatory
	DESCRIPTION
		"First_source_2_branch_17_output_current"
	::= { FirstGeneral_Precision_Distribution82Analog 717 }
First_source_2_branch_18_output_current OBJECT-TYPE
	SYNTAX INTEGER
	UNITS     "0.01 "
	ACCESS read-only
	STATUS mandatory
	DESCRIPTION
		"First_source_2_branch_18_output_current"
	::= { FirstGeneral_Precision_Distribution82Analog 718 }
First_source_2_branch_19_output_current OBJECT-TYPE
	SYNTAX INTEGER
	UNITS     "0.01 "
	ACCESS read-only
	STATUS mandatory
	DESCRIPTION
		"First_source_2_branch_19_output_current"
	::= { FirstGeneral_Precision_Distribution82Analog 719 }
First_source_2_branch_20_output_current OBJECT-TYPE
	SYNTAX INTEGER
	UNITS     "0.01 "
	ACCESS read-only
	STATUS mandatory
	DESCRIPTION
		"First_source_2_branch_20_output_current"
	::= { FirstGeneral_Precision_Distribution82Analog 720 }
First_source_2_branch_21_output_current OBJECT-TYPE
	SYNTAX INTEGER
	UNITS     "0.01 "
	ACCESS read-only
	STATUS mandatory
	DESCRIPTION
		"First_source_2_branch_21_output_current"
	::= { FirstGeneral_Precision_Distribution82Analog 721 }
First_source_2_branch_22_output_current OBJECT-TYPE
	SYNTAX INTEGER
	UNITS     "0.01 "
	ACCESS read-only
	STATUS mandatory
	DESCRIPTION
		"First_source_2_branch_22_output_current"
	::= { FirstGeneral_Precision_Distribution82Analog 722 }
First_source_2_branch_23_output_current OBJECT-TYPE
	SYNTAX INTEGER
	UNITS     "0.01 "
	ACCESS read-only
	STATUS mandatory
	DESCRIPTION
		"First_source_2_branch_23_output_current"
	::= { FirstGeneral_Precision_Distribution82Analog 723 }
First_source_2_branch_24_output_current OBJECT-TYPE
	SYNTAX INTEGER
	UNITS     "0.01 "
	ACCESS read-only
	STATUS mandatory
	DESCRIPTION
		"First_source_2_branch_24_output_current"
	::= { FirstGeneral_Precision_Distribution82Analog 724 }
First_source_2_branch_25_output_current OBJECT-TYPE
	SYNTAX INTEGER
	UNITS     "0.01 "
	ACCESS read-only
	STATUS mandatory
	DESCRIPTION
		"First_source_2_branch_25_output_current"
	::= { FirstGeneral_Precision_Distribution82Analog 725 }
First_source_2_branch_26_output_current OBJECT-TYPE
	SYNTAX INTEGER
	UNITS     "0.01 "
	ACCESS read-only
	STATUS mandatory
	DESCRIPTION
		"First_source_2_branch_26_output_current"
	::= { FirstGeneral_Precision_Distribution82Analog 726 }
First_source_2_branch_27_output_current OBJECT-TYPE
	SYNTAX INTEGER
	UNITS     "0.01 "
	ACCESS read-only
	STATUS mandatory
	DESCRIPTION
		"First_source_2_branch_27_output_current"
	::= { FirstGeneral_Precision_Distribution82Analog 727 }
First_source_2_branch_28_output_current OBJECT-TYPE
	SYNTAX INTEGER
	UNITS     "0.01 "
	ACCESS read-only
	STATUS mandatory
	DESCRIPTION
		"First_source_2_branch_28_output_current"
	::= { FirstGeneral_Precision_Distribution82Analog 728 }
First_source_2_branch_29_output_current OBJECT-TYPE
	SYNTAX INTEGER
	UNITS     "0.01 "
	ACCESS read-only
	STATUS mandatory
	DESCRIPTION
		"First_source_2_branch_29_output_current"
	::= { FirstGeneral_Precision_Distribution82Analog 729 }
First_source_2_branch_30_output_current OBJECT-TYPE
	SYNTAX INTEGER
	UNITS     "0.01 "
	ACCESS read-only
	STATUS mandatory
	DESCRIPTION
		"First_source_2_branch_30_output_current"
	::= { FirstGeneral_Precision_Distribution82Analog 730 }
First_source_2_branch_31_output_current OBJECT-TYPE
	SYNTAX INTEGER
	UNITS     "0.01 "
	ACCESS read-only
	STATUS mandatory
	DESCRIPTION
		"First_source_2_branch_31_output_current"
	::= { FirstGeneral_Precision_Distribution82Analog 731 }
First_source_2_branch_32_output_current OBJECT-TYPE
	SYNTAX INTEGER
	UNITS     "0.01 "
	ACCESS read-only
	STATUS mandatory
	DESCRIPTION
		"First_source_2_branch_32_output_current"
	::= { FirstGeneral_Precision_Distribution82Analog 732 }
First_source_2_branch_33_output_current OBJECT-TYPE
	SYNTAX INTEGER
	UNITS     "0.01 "
	ACCESS read-only
	STATUS mandatory
	DESCRIPTION
		"First_source_2_branch_33_output_current"
	::= { FirstGeneral_Precision_Distribution82Analog 733 }
First_source_2_branch_34_output_current OBJECT-TYPE
	SYNTAX INTEGER
	UNITS     "0.01 "
	ACCESS read-only
	STATUS mandatory
	DESCRIPTION
		"First_source_2_branch_34_output_current"
	::= { FirstGeneral_Precision_Distribution82Analog 734 }
First_source_2_branch_35_output_current OBJECT-TYPE
	SYNTAX INTEGER
	UNITS     "0.01 "
	ACCESS read-only
	STATUS mandatory
	DESCRIPTION
		"First_source_2_branch_35_output_current"
	::= { FirstGeneral_Precision_Distribution82Analog 735 }
First_source_2_branch_36_output_current OBJECT-TYPE
	SYNTAX INTEGER
	UNITS     "0.01 "
	ACCESS read-only
	STATUS mandatory
	DESCRIPTION
		"First_source_2_branch_36_output_current"
	::= { FirstGeneral_Precision_Distribution82Analog 736 }
First_source_2_branch_37_output_current OBJECT-TYPE
	SYNTAX INTEGER
	UNITS     "0.01 "
	ACCESS read-only
	STATUS mandatory
	DESCRIPTION
		"First_source_2_branch_37_output_current"
	::= { FirstGeneral_Precision_Distribution82Analog 737 }
First_source_2_branch_38_output_current OBJECT-TYPE
	SYNTAX INTEGER
	UNITS     "0.01 "
	ACCESS read-only
	STATUS mandatory
	DESCRIPTION
		"First_source_2_branch_38_output_current"
	::= { FirstGeneral_Precision_Distribution82Analog 738 }
First_source_2_branch_39_output_current OBJECT-TYPE
	SYNTAX INTEGER
	UNITS     "0.01 "
	ACCESS read-only
	STATUS mandatory
	DESCRIPTION
		"First_source_2_branch_39_output_current"
	::= { FirstGeneral_Precision_Distribution82Analog 739 }
First_source_2_branch_40_output_current OBJECT-TYPE
	SYNTAX INTEGER
	UNITS     "0.01 "
	ACCESS read-only
	STATUS mandatory
	DESCRIPTION
		"First_source_2_branch_40_output_current"
	::= { FirstGeneral_Precision_Distribution82Analog 740 }
First_source_2_branch_41_output_current OBJECT-TYPE
	SYNTAX INTEGER
	UNITS     "0.01 "
	ACCESS read-only
	STATUS mandatory
	DESCRIPTION
		"First_source_2_branch_41_output_current"
	::= { FirstGeneral_Precision_Distribution82Analog 741 }
First_source_2_branch_42_output_current OBJECT-TYPE
	SYNTAX INTEGER
	UNITS     "0.01 "
	ACCESS read-only
	STATUS mandatory
	DESCRIPTION
		"First_source_2_branch_42_output_current"
	::= { FirstGeneral_Precision_Distribution82Analog 742 }
First_source_2_branch_43_output_current OBJECT-TYPE
	SYNTAX INTEGER
	UNITS     "0.01 "
	ACCESS read-only
	STATUS mandatory
	DESCRIPTION
		"First_source_2_branch_43_output_current"
	::= { FirstGeneral_Precision_Distribution82Analog 743 }
First_source_2_branch_44_output_current OBJECT-TYPE
	SYNTAX INTEGER
	UNITS     "0.01 "
	ACCESS read-only
	STATUS mandatory
	DESCRIPTION
		"First_source_2_branch_44_output_current"
	::= { FirstGeneral_Precision_Distribution82Analog 744 }
First_source_2_branch_45_output_current OBJECT-TYPE
	SYNTAX INTEGER
	UNITS     "0.01 "
	ACCESS read-only
	STATUS mandatory
	DESCRIPTION
		"First_source_2_branch_45_output_current"
	::= { FirstGeneral_Precision_Distribution82Analog 745 }
First_source_2_branch_46_output_current OBJECT-TYPE
	SYNTAX INTEGER
	UNITS     "0.01 "
	ACCESS read-only
	STATUS mandatory
	DESCRIPTION
		"First_source_2_branch_46_output_current"
	::= { FirstGeneral_Precision_Distribution82Analog 746 }
First_source_2_branch_47_output_current OBJECT-TYPE
	SYNTAX INTEGER
	UNITS     "0.01 "
	ACCESS read-only
	STATUS mandatory
	DESCRIPTION
		"First_source_2_branch_47_output_current"
	::= { FirstGeneral_Precision_Distribution82Analog 747 }
First_source_2_branch_48_output_current OBJECT-TYPE
	SYNTAX INTEGER
	UNITS     "0.01 "
	ACCESS read-only
	STATUS mandatory
	DESCRIPTION
		"First_source_2_branch_48_output_current"
	::= { FirstGeneral_Precision_Distribution82Analog 748 }
First_source_2_branch_49_output_current OBJECT-TYPE
	SYNTAX INTEGER
	UNITS     "0.01 "
	ACCESS read-only
	STATUS mandatory
	DESCRIPTION
		"First_source_2_branch_49_output_current"
	::= { FirstGeneral_Precision_Distribution82Analog 749 }
First_source_2_branch_50_output_current OBJECT-TYPE
	SYNTAX INTEGER
	UNITS     "0.01 "
	ACCESS read-only
	STATUS mandatory
	DESCRIPTION
		"First_source_2_branch_50_output_current"
	::= { FirstGeneral_Precision_Distribution82Analog 750 }
First_source_2_branch_51_output_current OBJECT-TYPE
	SYNTAX INTEGER
	UNITS     "0.01 "
	ACCESS read-only
	STATUS mandatory
	DESCRIPTION
		"First_source_2_branch_51_output_current"
	::= { FirstGeneral_Precision_Distribution82Analog 751 }
First_source_2_branch_52_output_current OBJECT-TYPE
	SYNTAX INTEGER
	UNITS     "0.01 "
	ACCESS read-only
	STATUS mandatory
	DESCRIPTION
		"First_source_2_branch_52_output_current"
	::= { FirstGeneral_Precision_Distribution82Analog 752 }
First_source_2_branch_53_output_current OBJECT-TYPE
	SYNTAX INTEGER
	UNITS     "0.01 "
	ACCESS read-only
	STATUS mandatory
	DESCRIPTION
		"First_source_2_branch_53_output_current"
	::= { FirstGeneral_Precision_Distribution82Analog 753 }
First_source_2_branch_54_output_current OBJECT-TYPE
	SYNTAX INTEGER
	UNITS     "0.01 "
	ACCESS read-only
	STATUS mandatory
	DESCRIPTION
		"First_source_2_branch_54_output_current"
	::= { FirstGeneral_Precision_Distribution82Analog 754 }
First_source_2_branch_55_output_current OBJECT-TYPE
	SYNTAX INTEGER
	UNITS     "0.01 "
	ACCESS read-only
	STATUS mandatory
	DESCRIPTION
		"First_source_2_branch_55_output_current"
	::= { FirstGeneral_Precision_Distribution82Analog 755 }
First_source_2_branch_56_output_current OBJECT-TYPE
	SYNTAX INTEGER
	UNITS     "0.01 "
	ACCESS read-only
	STATUS mandatory
	DESCRIPTION
		"First_source_2_branch_56_output_current"
	::= { FirstGeneral_Precision_Distribution82Analog 756 }
First_source_2_branch_57_output_current OBJECT-TYPE
	SYNTAX INTEGER
	UNITS     "0.01 "
	ACCESS read-only
	STATUS mandatory
	DESCRIPTION
		"First_source_2_branch_57_output_current"
	::= { FirstGeneral_Precision_Distribution82Analog 757 }
First_source_2_branch_58_output_current OBJECT-TYPE
	SYNTAX INTEGER
	UNITS     "0.01 "
	ACCESS read-only
	STATUS mandatory
	DESCRIPTION
		"First_source_2_branch_58_output_current"
	::= { FirstGeneral_Precision_Distribution82Analog 758 }
First_source_2_branch_59_output_current OBJECT-TYPE
	SYNTAX INTEGER
	UNITS     "0.01 "
	ACCESS read-only
	STATUS mandatory
	DESCRIPTION
		"First_source_2_branch_59_output_current"
	::= { FirstGeneral_Precision_Distribution82Analog 759 }
First_source_2_branch_60_output_current OBJECT-TYPE
	SYNTAX INTEGER
	UNITS     "0.01 "
	ACCESS read-only
	STATUS mandatory
	DESCRIPTION
		"First_source_2_branch_60_output_current"
	::= { FirstGeneral_Precision_Distribution82Analog 760 }
First_source_2_branch_61_output_current OBJECT-TYPE
	SYNTAX INTEGER
	UNITS     "0.01 "
	ACCESS read-only
	STATUS mandatory
	DESCRIPTION
		"First_source_2_branch_61_output_current"
	::= { FirstGeneral_Precision_Distribution82Analog 761 }
First_source_2_branch_62_output_current OBJECT-TYPE
	SYNTAX INTEGER
	UNITS     "0.01 "
	ACCESS read-only
	STATUS mandatory
	DESCRIPTION
		"First_source_2_branch_62_output_current"
	::= { FirstGeneral_Precision_Distribution82Analog 762 }
First_source_2_branch_63_output_current OBJECT-TYPE
	SYNTAX INTEGER
	UNITS     "0.01 "
	ACCESS read-only
	STATUS mandatory
	DESCRIPTION
		"First_source_2_branch_63_output_current"
	::= { FirstGeneral_Precision_Distribution82Analog 763 }
First_source_2_branch_64_output_current OBJECT-TYPE
	SYNTAX INTEGER
	UNITS     "0.01 "
	ACCESS read-only
	STATUS mandatory
	DESCRIPTION
		"First_source_2_branch_64_output_current"
	::= { FirstGeneral_Precision_Distribution82Analog 764 }
First_source_2_branch_65_output_current OBJECT-TYPE
	SYNTAX INTEGER
	UNITS     "0.01 "
	ACCESS read-only
	STATUS mandatory
	DESCRIPTION
		"First_source_2_branch_65_output_current"
	::= { FirstGeneral_Precision_Distribution82Analog 765 }
First_source_2_branch_66_output_current OBJECT-TYPE
	SYNTAX INTEGER
	UNITS     "0.01 "
	ACCESS read-only
	STATUS mandatory
	DESCRIPTION
		"First_source_2_branch_66_output_current"
	::= { FirstGeneral_Precision_Distribution82Analog 766 }
First_source_2_branch_67_output_current OBJECT-TYPE
	SYNTAX INTEGER
	UNITS     "0.01 "
	ACCESS read-only
	STATUS mandatory
	DESCRIPTION
		"First_source_2_branch_67_output_current"
	::= { FirstGeneral_Precision_Distribution82Analog 767 }
First_source_2_branch_68_output_current OBJECT-TYPE
	SYNTAX INTEGER
	UNITS     "0.01 "
	ACCESS read-only
	STATUS mandatory
	DESCRIPTION
		"First_source_2_branch_68_output_current"
	::= { FirstGeneral_Precision_Distribution82Analog 768 }
First_source_2_branch_69_output_current OBJECT-TYPE
	SYNTAX INTEGER
	UNITS     "0.01 "
	ACCESS read-only
	STATUS mandatory
	DESCRIPTION
		"First_source_2_branch_69_output_current"
	::= { FirstGeneral_Precision_Distribution82Analog 769 }
First_source_2_branch_70_output_current OBJECT-TYPE
	SYNTAX INTEGER
	UNITS     "0.01 "
	ACCESS read-only
	STATUS mandatory
	DESCRIPTION
		"First_source_2_branch_70_output_current"
	::= { FirstGeneral_Precision_Distribution82Analog 770 }
First_source_2_branch_71_output_current OBJECT-TYPE
	SYNTAX INTEGER
	UNITS     "0.01 "
	ACCESS read-only
	STATUS mandatory
	DESCRIPTION
		"First_source_2_branch_71_output_current"
	::= { FirstGeneral_Precision_Distribution82Analog 771 }
First_source_2_branch_72_output_current OBJECT-TYPE
	SYNTAX INTEGER
	UNITS     "0.01 "
	ACCESS read-only
	STATUS mandatory
	DESCRIPTION
		"First_source_2_branch_72_output_current"
	::= { FirstGeneral_Precision_Distribution82Analog 772 }
First_source_2_branch_73_output_current OBJECT-TYPE
	SYNTAX INTEGER
	UNITS     "0.01 "
	ACCESS read-only
	STATUS mandatory
	DESCRIPTION
		"First_source_2_branch_73_output_current"
	::= { FirstGeneral_Precision_Distribution82Analog 773 }
First_source_2_branch_74_output_current OBJECT-TYPE
	SYNTAX INTEGER
	UNITS     "0.01 "
	ACCESS read-only
	STATUS mandatory
	DESCRIPTION
		"First_source_2_branch_74_output_current"
	::= { FirstGeneral_Precision_Distribution82Analog 774 }
First_source_2_branch_75_output_current OBJECT-TYPE
	SYNTAX INTEGER
	UNITS     "0.01 "
	ACCESS read-only
	STATUS mandatory
	DESCRIPTION
		"First_source_2_branch_75_output_current"
	::= { FirstGeneral_Precision_Distribution82Analog 775 }
First_source_2_branch_76_output_current OBJECT-TYPE
	SYNTAX INTEGER
	UNITS     "0.01 "
	ACCESS read-only
	STATUS mandatory
	DESCRIPTION
		"First_source_2_branch_76_output_current"
	::= { FirstGeneral_Precision_Distribution82Analog 776 }
First_source_2_branch_77_output_current OBJECT-TYPE
	SYNTAX INTEGER
	UNITS     "0.01 "
	ACCESS read-only
	STATUS mandatory
	DESCRIPTION
		"First_source_2_branch_77_output_current"
	::= { FirstGeneral_Precision_Distribution82Analog 777 }
First_source_2_branch_78_output_current OBJECT-TYPE
	SYNTAX INTEGER
	UNITS     "0.01 "
	ACCESS read-only
	STATUS mandatory
	DESCRIPTION
		"First_source_2_branch_78_output_current"
	::= { FirstGeneral_Precision_Distribution82Analog 778 }
First_source_2_branch_79_output_current OBJECT-TYPE
	SYNTAX INTEGER
	UNITS     "0.01 "
	ACCESS read-only
	STATUS mandatory
	DESCRIPTION
		"First_source_2_branch_79_output_current"
	::= { FirstGeneral_Precision_Distribution82Analog 779 }
First_source_2_branch_80_output_current OBJECT-TYPE
	SYNTAX INTEGER
	UNITS     "0.01 "
	ACCESS read-only
	STATUS mandatory
	DESCRIPTION
		"First_source_2_branch_80_output_current"
	::= { FirstGeneral_Precision_Distribution82Analog 780 }
First_source_2_branch_81_output_current OBJECT-TYPE
	SYNTAX INTEGER
	UNITS     "0.01 "
	ACCESS read-only
	STATUS mandatory
	DESCRIPTION
		"First_source_2_branch_81_output_current"
	::= { FirstGeneral_Precision_Distribution82Analog 781 }
First_source_2_branch_82_output_current OBJECT-TYPE
	SYNTAX INTEGER
	UNITS     "0.01 "
	ACCESS read-only
	STATUS mandatory
	DESCRIPTION
		"First_source_2_branch_82_output_current"
	::= { FirstGeneral_Precision_Distribution82Analog 782 }
First_source_2_branch_83_output_current OBJECT-TYPE
	SYNTAX INTEGER
	UNITS     "0.01 "
	ACCESS read-only
	STATUS mandatory
	DESCRIPTION
		"First_source_2_branch_83_output_current"
	::= { FirstGeneral_Precision_Distribution82Analog 783 }
First_source_2_branch_84_output_current OBJECT-TYPE
	SYNTAX INTEGER
	UNITS     "0.01 "
	ACCESS read-only
	STATUS mandatory
	DESCRIPTION
		"First_source_2_branch_84_output_current"
	::= { FirstGeneral_Precision_Distribution82Analog 784 }
First_source_2_branch_85_output_current OBJECT-TYPE
	SYNTAX INTEGER
	UNITS     "0.01 "
	ACCESS read-only
	STATUS mandatory
	DESCRIPTION
		"First_source_2_branch_85_output_current"
	::= { FirstGeneral_Precision_Distribution82Analog 785 }
First_source_2_branch_86_output_current OBJECT-TYPE
	SYNTAX INTEGER
	UNITS     "0.01 "
	ACCESS read-only
	STATUS mandatory
	DESCRIPTION
		"First_source_2_branch_86_output_current"
	::= { FirstGeneral_Precision_Distribution82Analog 786 }
First_source_2_branch_87_output_current OBJECT-TYPE
	SYNTAX INTEGER
	UNITS     "0.01 "
	ACCESS read-only
	STATUS mandatory
	DESCRIPTION
		"First_source_2_branch_87_output_current"
	::= { FirstGeneral_Precision_Distribution82Analog 787 }
First_source_2_branch_88_output_current OBJECT-TYPE
	SYNTAX INTEGER
	UNITS     "0.01 "
	ACCESS read-only
	STATUS mandatory
	DESCRIPTION
		"First_source_2_branch_88_output_current"
	::= { FirstGeneral_Precision_Distribution82Analog 788 }
First_source_2_branch_89_output_current OBJECT-TYPE
	SYNTAX INTEGER
	UNITS     "0.01 "
	ACCESS read-only
	STATUS mandatory
	DESCRIPTION
		"First_source_2_branch_89_output_current"
	::= { FirstGeneral_Precision_Distribution82Analog 789 }
First_source_2_branch_90_output_current OBJECT-TYPE
	SYNTAX INTEGER
	UNITS     "0.01 "
	ACCESS read-only
	STATUS mandatory
	DESCRIPTION
		"First_source_2_branch_90_output_current"
	::= { FirstGeneral_Precision_Distribution82Analog 790 }
First_source_2_branch_91_output_current OBJECT-TYPE
	SYNTAX INTEGER
	UNITS     "0.01 "
	ACCESS read-only
	STATUS mandatory
	DESCRIPTION
		"First_source_2_branch_91_output_current"
	::= { FirstGeneral_Precision_Distribution82Analog 791 }
First_source_2_branch_92_output_current OBJECT-TYPE
	SYNTAX INTEGER
	UNITS     "0.01 "
	ACCESS read-only
	STATUS mandatory
	DESCRIPTION
		"First_source_2_branch_92_output_current"
	::= { FirstGeneral_Precision_Distribution82Analog 792 }
First_source_2_branch_93_output_current OBJECT-TYPE
	SYNTAX INTEGER
	UNITS     "0.01 "
	ACCESS read-only
	STATUS mandatory
	DESCRIPTION
		"First_source_2_branch_93_output_current"
	::= { FirstGeneral_Precision_Distribution82Analog 793 }
First_source_2_branch_94_output_current OBJECT-TYPE
	SYNTAX INTEGER
	UNITS     "0.01 "
	ACCESS read-only
	STATUS mandatory
	DESCRIPTION
		"First_source_2_branch_94_output_current"
	::= { FirstGeneral_Precision_Distribution82Analog 794 }
First_source_2_branch_95_output_current OBJECT-TYPE
	SYNTAX INTEGER
	UNITS     "0.01 "
	ACCESS read-only
	STATUS mandatory
	DESCRIPTION
		"First_source_2_branch_95_output_current"
	::= { FirstGeneral_Precision_Distribution82Analog 795 }
First_source_2_branch_96_output_current OBJECT-TYPE
	SYNTAX INTEGER
	UNITS     "0.01 "
	ACCESS read-only
	STATUS mandatory
	DESCRIPTION
		"First_source_2_branch_96_output_current"
	::= { FirstGeneral_Precision_Distribution82Analog 796 }
First_source_2_branch_97_output_current OBJECT-TYPE
	SYNTAX INTEGER
	UNITS     "0.01 "
	ACCESS read-only
	STATUS mandatory
	DESCRIPTION
		"First_source_2_branch_97_output_current"
	::= { FirstGeneral_Precision_Distribution82Analog 797 }
First_source_2_branch_98_output_current OBJECT-TYPE
	SYNTAX INTEGER
	UNITS     "0.01 "
	ACCESS read-only
	STATUS mandatory
	DESCRIPTION
		"First_source_2_branch_98_output_current"
	::= { FirstGeneral_Precision_Distribution82Analog 798 }
First_source_2_branch_99_output_current OBJECT-TYPE
	SYNTAX INTEGER
	UNITS     "0.01 "
	ACCESS read-only
	STATUS mandatory
	DESCRIPTION
		"First_source_2_branch_99_output_current"
	::= { FirstGeneral_Precision_Distribution82Analog 799 }
First_source_2_branch_100_output_current OBJECT-TYPE
	SYNTAX INTEGER
	UNITS     "0.01 "
	ACCESS read-only
	STATUS mandatory
	DESCRIPTION
		"First_source_2_branch_100_output_current"
	::= { FirstGeneral_Precision_Distribution82Analog 800 }
First_source_2_branch_1_output_power OBJECT-TYPE
	SYNTAX INTEGER
	UNITS     "0.01KW "
	ACCESS read-only
	STATUS mandatory
	DESCRIPTION
		"First_source_2_branch_1_output_power"
	::= { FirstGeneral_Precision_Distribution82Analog 801 }
First_source_2_branch_2_output_power OBJECT-TYPE
	SYNTAX INTEGER
	UNITS     "0.01 "
	ACCESS read-only
	STATUS mandatory
	DESCRIPTION
		"First_source_2_branch_2_output_power"
	::= { FirstGeneral_Precision_Distribution82Analog 802 }
First_source_2_branch_3_output_power OBJECT-TYPE
	SYNTAX INTEGER
	UNITS     "0.01 "
	ACCESS read-only
	STATUS mandatory
	DESCRIPTION
		"First_source_2_branch_3_output_power"
	::= { FirstGeneral_Precision_Distribution82Analog 803 }
First_source_2_branch_4_output_power OBJECT-TYPE
	SYNTAX INTEGER
	UNITS     "0.01 "
	ACCESS read-only
	STATUS mandatory
	DESCRIPTION
		"First_source_2_branch_4_output_power"
	::= { FirstGeneral_Precision_Distribution82Analog 804 }
First_source_2_branch_5_output_power OBJECT-TYPE
	SYNTAX INTEGER
	UNITS     "0.01 "
	ACCESS read-only
	STATUS mandatory
	DESCRIPTION
		"First_source_2_branch_5_output_power"
	::= { FirstGeneral_Precision_Distribution82Analog 805 }
First_source_2_branch_6_output_power OBJECT-TYPE
	SYNTAX INTEGER
	UNITS     "0.01 "
	ACCESS read-only
	STATUS mandatory
	DESCRIPTION
		"First_source_2_branch_6_output_power"
	::= { FirstGeneral_Precision_Distribution82Analog 806 }
First_source_2_branch_7_output_power OBJECT-TYPE
	SYNTAX INTEGER
	UNITS     "0.01 "
	ACCESS read-only
	STATUS mandatory
	DESCRIPTION
		"First_source_2_branch_7_output_power"
	::= { FirstGeneral_Precision_Distribution82Analog 807 }
First_source_2_branch_8_output_power OBJECT-TYPE
	SYNTAX INTEGER
	UNITS     "0.01 "
	ACCESS read-only
	STATUS mandatory
	DESCRIPTION
		"First_source_2_branch_8_output_power"
	::= { FirstGeneral_Precision_Distribution82Analog 808 }
First_source_2_branch_9_output_power OBJECT-TYPE
	SYNTAX INTEGER
	UNITS     "0.01 "
	ACCESS read-only
	STATUS mandatory
	DESCRIPTION
		"First_source_2_branch_9_output_power"
	::= { FirstGeneral_Precision_Distribution82Analog 809 }
First_source_2_branch_10_output_power OBJECT-TYPE
	SYNTAX INTEGER
	UNITS     "0.01 "
	ACCESS read-only
	STATUS mandatory
	DESCRIPTION
		"First_source_2_branch_10_output_power"
	::= { FirstGeneral_Precision_Distribution82Analog 810 }
First_source_2_branch_11_output_power OBJECT-TYPE
	SYNTAX INTEGER
	UNITS     "0.01 "
	ACCESS read-only
	STATUS mandatory
	DESCRIPTION
		"First_source_2_branch_11_output_power"
	::= { FirstGeneral_Precision_Distribution82Analog 811 }
First_source_2_branch_12_output_power OBJECT-TYPE
	SYNTAX INTEGER
	UNITS     "0.01 "
	ACCESS read-only
	STATUS mandatory
	DESCRIPTION
		"First_source_2_branch_12_output_power"
	::= { FirstGeneral_Precision_Distribution82Analog 812 }
First_source_2_branch_13_output_power OBJECT-TYPE
	SYNTAX INTEGER
	UNITS     "0.01 "
	ACCESS read-only
	STATUS mandatory
	DESCRIPTION
		"First_source_2_branch_13_output_power"
	::= { FirstGeneral_Precision_Distribution82Analog 813 }
First_source_2_branch_14_output_power OBJECT-TYPE
	SYNTAX INTEGER
	UNITS     "0.01 "
	ACCESS read-only
	STATUS mandatory
	DESCRIPTION
		"First_source_2_branch_14_output_power"
	::= { FirstGeneral_Precision_Distribution82Analog 814 }
First_source_2_branch_15_output_power OBJECT-TYPE
	SYNTAX INTEGER
	UNITS     "0.01 "
	ACCESS read-only
	STATUS mandatory
	DESCRIPTION
		"First_source_2_branch_15_output_power"
	::= { FirstGeneral_Precision_Distribution82Analog 815 }
First_source_2_branch_16_output_power OBJECT-TYPE
	SYNTAX INTEGER
	UNITS     "0.01 "
	ACCESS read-only
	STATUS mandatory
	DESCRIPTION
		"First_source_2_branch_16_output_power"
	::= { FirstGeneral_Precision_Distribution82Analog 816 }
First_source_2_branch_17_output_power OBJECT-TYPE
	SYNTAX INTEGER
	UNITS     "0.01 "
	ACCESS read-only
	STATUS mandatory
	DESCRIPTION
		"First_source_2_branch_17_output_power"
	::= { FirstGeneral_Precision_Distribution82Analog 817 }
First_source_2_branch_18_output_power OBJECT-TYPE
	SYNTAX INTEGER
	UNITS     "0.01 "
	ACCESS read-only
	STATUS mandatory
	DESCRIPTION
		"First_source_2_branch_18_output_power"
	::= { FirstGeneral_Precision_Distribution82Analog 818 }
First_source_2_branch_19_output_power OBJECT-TYPE
	SYNTAX INTEGER
	UNITS     "0.01 "
	ACCESS read-only
	STATUS mandatory
	DESCRIPTION
		"First_source_2_branch_19_output_power"
	::= { FirstGeneral_Precision_Distribution82Analog 819 }
First_source_2_branch_20_output_power OBJECT-TYPE
	SYNTAX INTEGER
	UNITS     "0.01 "
	ACCESS read-only
	STATUS mandatory
	DESCRIPTION
		"First_source_2_branch_20_output_power"
	::= { FirstGeneral_Precision_Distribution82Analog 820 }
First_source_2_branch_21_output_power OBJECT-TYPE
	SYNTAX INTEGER
	UNITS     "0.01 "
	ACCESS read-only
	STATUS mandatory
	DESCRIPTION
		"First_source_2_branch_21_output_power"
	::= { FirstGeneral_Precision_Distribution82Analog 821 }
First_source_2_branch_22_output_power OBJECT-TYPE
	SYNTAX INTEGER
	UNITS     "0.01 "
	ACCESS read-only
	STATUS mandatory
	DESCRIPTION
		"First_source_2_branch_22_output_power"
	::= { FirstGeneral_Precision_Distribution82Analog 822 }
First_source_2_branch_23_output_power OBJECT-TYPE
	SYNTAX INTEGER
	UNITS     "0.01 "
	ACCESS read-only
	STATUS mandatory
	DESCRIPTION
		"First_source_2_branch_23_output_power"
	::= { FirstGeneral_Precision_Distribution82Analog 823 }
First_source_2_branch_24_output_power OBJECT-TYPE
	SYNTAX INTEGER
	UNITS     "0.01 "
	ACCESS read-only
	STATUS mandatory
	DESCRIPTION
		"First_source_2_branch_24_output_power"
	::= { FirstGeneral_Precision_Distribution82Analog 824 }
First_source_2_branch_25_output_power OBJECT-TYPE
	SYNTAX INTEGER
	UNITS     "0.01 "
	ACCESS read-only
	STATUS mandatory
	DESCRIPTION
		"First_source_2_branch_25_output_power"
	::= { FirstGeneral_Precision_Distribution82Analog 825 }
First_source_2_branch_26_output_power OBJECT-TYPE
	SYNTAX INTEGER
	UNITS     "0.01 "
	ACCESS read-only
	STATUS mandatory
	DESCRIPTION
		"First_source_2_branch_26_output_power"
	::= { FirstGeneral_Precision_Distribution82Analog 826 }
First_source_2_branch_27_output_power OBJECT-TYPE
	SYNTAX INTEGER
	UNITS     "0.01 "
	ACCESS read-only
	STATUS mandatory
	DESCRIPTION
		"First_source_2_branch_27_output_power"
	::= { FirstGeneral_Precision_Distribution82Analog 827 }
First_source_2_branch_28_output_power OBJECT-TYPE
	SYNTAX INTEGER
	UNITS     "0.01 "
	ACCESS read-only
	STATUS mandatory
	DESCRIPTION
		"First_source_2_branch_28_output_power"
	::= { FirstGeneral_Precision_Distribution82Analog 828 }
First_source_2_branch_29_output_power OBJECT-TYPE
	SYNTAX INTEGER
	UNITS     "0.01 "
	ACCESS read-only
	STATUS mandatory
	DESCRIPTION
		"First_source_2_branch_29_output_power"
	::= { FirstGeneral_Precision_Distribution82Analog 829 }
First_source_2_branch_30_output_power OBJECT-TYPE
	SYNTAX INTEGER
	UNITS     "0.01 "
	ACCESS read-only
	STATUS mandatory
	DESCRIPTION
		"First_source_2_branch_30_output_power"
	::= { FirstGeneral_Precision_Distribution82Analog 830 }
First_source_2_branch_31_output_power OBJECT-TYPE
	SYNTAX INTEGER
	UNITS     "0.01 "
	ACCESS read-only
	STATUS mandatory
	DESCRIPTION
		"First_source_2_branch_31_output_power"
	::= { FirstGeneral_Precision_Distribution82Analog 831 }
First_source_2_branch_32_output_power OBJECT-TYPE
	SYNTAX INTEGER
	UNITS     "0.01 "
	ACCESS read-only
	STATUS mandatory
	DESCRIPTION
		"First_source_2_branch_32_output_power"
	::= { FirstGeneral_Precision_Distribution82Analog 832 }
First_source_2_branch_33_output_power OBJECT-TYPE
	SYNTAX INTEGER
	UNITS     "0.01 "
	ACCESS read-only
	STATUS mandatory
	DESCRIPTION
		"First_source_2_branch_33_output_power"
	::= { FirstGeneral_Precision_Distribution82Analog 833 }
First_source_2_branch_34_output_power OBJECT-TYPE
	SYNTAX INTEGER
	UNITS     "0.01 "
	ACCESS read-only
	STATUS mandatory
	DESCRIPTION
		"First_source_2_branch_34_output_power"
	::= { FirstGeneral_Precision_Distribution82Analog 834 }
First_source_2_branch_35_output_power OBJECT-TYPE
	SYNTAX INTEGER
	UNITS     "0.01 "
	ACCESS read-only
	STATUS mandatory
	DESCRIPTION
		"First_source_2_branch_35_output_power"
	::= { FirstGeneral_Precision_Distribution82Analog 835 }
First_source_2_branch_36_output_power OBJECT-TYPE
	SYNTAX INTEGER
	UNITS     "0.01 "
	ACCESS read-only
	STATUS mandatory
	DESCRIPTION
		"First_source_2_branch_36_output_power"
	::= { FirstGeneral_Precision_Distribution82Analog 836 }
First_source_2_branch_37_output_power OBJECT-TYPE
	SYNTAX INTEGER
	UNITS     "0.01 "
	ACCESS read-only
	STATUS mandatory
	DESCRIPTION
		"First_source_2_branch_37_output_power"
	::= { FirstGeneral_Precision_Distribution82Analog 837 }
First_source_2_branch_38_output_power OBJECT-TYPE
	SYNTAX INTEGER
	UNITS     "0.01 "
	ACCESS read-only
	STATUS mandatory
	DESCRIPTION
		"First_source_2_branch_38_output_power"
	::= { FirstGeneral_Precision_Distribution82Analog 838 }
First_source_2_branch_39_output_power OBJECT-TYPE
	SYNTAX INTEGER
	UNITS     "0.01 "
	ACCESS read-only
	STATUS mandatory
	DESCRIPTION
		"First_source_2_branch_39_output_power"
	::= { FirstGeneral_Precision_Distribution82Analog 839 }
First_source_2_branch_40_output_power OBJECT-TYPE
	SYNTAX INTEGER
	UNITS     "0.01 "
	ACCESS read-only
	STATUS mandatory
	DESCRIPTION
		"First_source_2_branch_40_output_power"
	::= { FirstGeneral_Precision_Distribution82Analog 840 }
First_source_2_branch_41_output_power OBJECT-TYPE
	SYNTAX INTEGER
	UNITS     "0.01 "
	ACCESS read-only
	STATUS mandatory
	DESCRIPTION
		"First_source_2_branch_41_output_power"
	::= { FirstGeneral_Precision_Distribution82Analog 841 }
First_source_2_branch_42_output_power OBJECT-TYPE
	SYNTAX INTEGER
	UNITS     "0.01 "
	ACCESS read-only
	STATUS mandatory
	DESCRIPTION
		"First_source_2_branch_42_output_power"
	::= { FirstGeneral_Precision_Distribution82Analog 842 }
First_source_2_branch_43_output_power OBJECT-TYPE
	SYNTAX INTEGER
	UNITS     "0.01 "
	ACCESS read-only
	STATUS mandatory
	DESCRIPTION
		"First_source_2_branch_43_output_power"
	::= { FirstGeneral_Precision_Distribution82Analog 843 }
First_source_2_branch_44_output_power OBJECT-TYPE
	SYNTAX INTEGER
	UNITS     "0.01 "
	ACCESS read-only
	STATUS mandatory
	DESCRIPTION
		"First_source_2_branch_44_output_power"
	::= { FirstGeneral_Precision_Distribution82Analog 844 }
First_source_2_branch_45_output_power OBJECT-TYPE
	SYNTAX INTEGER
	UNITS     "0.01 "
	ACCESS read-only
	STATUS mandatory
	DESCRIPTION
		"First_source_2_branch_45_output_power"
	::= { FirstGeneral_Precision_Distribution82Analog 845 }
First_source_2_branch_46_output_power OBJECT-TYPE
	SYNTAX INTEGER
	UNITS     "0.01 "
	ACCESS read-only
	STATUS mandatory
	DESCRIPTION
		"First_source_2_branch_46_output_power"
	::= { FirstGeneral_Precision_Distribution82Analog 846 }
First_source_2_branch_47_output_power OBJECT-TYPE
	SYNTAX INTEGER
	UNITS     "0.01 "
	ACCESS read-only
	STATUS mandatory
	DESCRIPTION
		"First_source_2_branch_47_output_power"
	::= { FirstGeneral_Precision_Distribution82Analog 847 }
First_source_2_branch_48_output_power OBJECT-TYPE
	SYNTAX INTEGER
	UNITS     "0.01 "
	ACCESS read-only
	STATUS mandatory
	DESCRIPTION
		"First_source_2_branch_48_output_power"
	::= { FirstGeneral_Precision_Distribution82Analog 848 }
First_source_2_branch_49_output_power OBJECT-TYPE
	SYNTAX INTEGER
	UNITS     "0.01 "
	ACCESS read-only
	STATUS mandatory
	DESCRIPTION
		"First_source_2_branch_49_output_power"
	::= { FirstGeneral_Precision_Distribution82Analog 849 }
First_source_2_branch_50_output_power OBJECT-TYPE
	SYNTAX INTEGER
	UNITS     "0.01 "
	ACCESS read-only
	STATUS mandatory
	DESCRIPTION
		"First_source_2_branch_50_output_power"
	::= { FirstGeneral_Precision_Distribution82Analog 850 }
First_source_2_branch_51_output_power OBJECT-TYPE
	SYNTAX INTEGER
	UNITS     "0.01 "
	ACCESS read-only
	STATUS mandatory
	DESCRIPTION
		"First_source_2_branch_51_output_power"
	::= { FirstGeneral_Precision_Distribution82Analog 851 }
First_source_2_branch_52_output_power OBJECT-TYPE
	SYNTAX INTEGER
	UNITS     "0.01 "
	ACCESS read-only
	STATUS mandatory
	DESCRIPTION
		"First_source_2_branch_52_output_power"
	::= { FirstGeneral_Precision_Distribution82Analog 852 }
First_source_2_branch_53_output_power OBJECT-TYPE
	SYNTAX INTEGER
	UNITS     "0.01 "
	ACCESS read-only
	STATUS mandatory
	DESCRIPTION
		"First_source_2_branch_53_output_power"
	::= { FirstGeneral_Precision_Distribution82Analog 853 }
First_source_2_branch_54_output_power OBJECT-TYPE
	SYNTAX INTEGER
	UNITS     "0.01 "
	ACCESS read-only
	STATUS mandatory
	DESCRIPTION
		"First_source_2_branch_54_output_power"
	::= { FirstGeneral_Precision_Distribution82Analog 854 }
First_source_2_branch_55_output_power OBJECT-TYPE
	SYNTAX INTEGER
	UNITS     "0.01 "
	ACCESS read-only
	STATUS mandatory
	DESCRIPTION
		"First_source_2_branch_55_output_power"
	::= { FirstGeneral_Precision_Distribution82Analog 855 }
First_source_2_branch_56_output_power OBJECT-TYPE
	SYNTAX INTEGER
	UNITS     "0.01 "
	ACCESS read-only
	STATUS mandatory
	DESCRIPTION
		"First_source_2_branch_56_output_power"
	::= { FirstGeneral_Precision_Distribution82Analog 856 }
First_source_2_branch_57_output_power OBJECT-TYPE
	SYNTAX INTEGER
	UNITS     "0.01 "
	ACCESS read-only
	STATUS mandatory
	DESCRIPTION
		"First_source_2_branch_57_output_power"
	::= { FirstGeneral_Precision_Distribution82Analog 857 }
First_source_2_branch_58_output_power OBJECT-TYPE
	SYNTAX INTEGER
	UNITS     "0.01 "
	ACCESS read-only
	STATUS mandatory
	DESCRIPTION
		"First_source_2_branch_58_output_power"
	::= { FirstGeneral_Precision_Distribution82Analog 858 }
First_source_2_branch_59_output_power OBJECT-TYPE
	SYNTAX INTEGER
	UNITS     "0.01 "
	ACCESS read-only
	STATUS mandatory
	DESCRIPTION
		"First_source_2_branch_59_output_power"
	::= { FirstGeneral_Precision_Distribution82Analog 859 }
First_source_2_branch_60_output_power OBJECT-TYPE
	SYNTAX INTEGER
	UNITS     "0.01 "
	ACCESS read-only
	STATUS mandatory
	DESCRIPTION
		"First_source_2_branch_60_output_power"
	::= { FirstGeneral_Precision_Distribution82Analog 860 }
First_source_2_branch_61_output_power OBJECT-TYPE
	SYNTAX INTEGER
	UNITS     "0.01 "
	ACCESS read-only
	STATUS mandatory
	DESCRIPTION
		"First_source_2_branch_61_output_power"
	::= { FirstGeneral_Precision_Distribution82Analog 861 }
First_source_2_branch_62_output_power OBJECT-TYPE
	SYNTAX INTEGER
	UNITS     "0.01 "
	ACCESS read-only
	STATUS mandatory
	DESCRIPTION
		"First_source_2_branch_62_output_power"
	::= { FirstGeneral_Precision_Distribution82Analog 862 }
First_source_2_branch_63_output_power OBJECT-TYPE
	SYNTAX INTEGER
	UNITS     "0.01 "
	ACCESS read-only
	STATUS mandatory
	DESCRIPTION
		"First_source_2_branch_63_output_power"
	::= { FirstGeneral_Precision_Distribution82Analog 863 }
First_source_2_branch_64_output_power OBJECT-TYPE
	SYNTAX INTEGER
	UNITS     "0.01 "
	ACCESS read-only
	STATUS mandatory
	DESCRIPTION
		"First_source_2_branch_64_output_power"
	::= { FirstGeneral_Precision_Distribution82Analog 864 }
First_source_2_branch_65_output_power OBJECT-TYPE
	SYNTAX INTEGER
	UNITS     "0.01 "
	ACCESS read-only
	STATUS mandatory
	DESCRIPTION
		"First_source_2_branch_65_output_power"
	::= { FirstGeneral_Precision_Distribution82Analog 865 }
First_source_2_branch_66_output_power OBJECT-TYPE
	SYNTAX INTEGER
	UNITS     "0.01 "
	ACCESS read-only
	STATUS mandatory
	DESCRIPTION
		"First_source_2_branch_66_output_power"
	::= { FirstGeneral_Precision_Distribution82Analog 866 }
First_source_2_branch_67_output_power OBJECT-TYPE
	SYNTAX INTEGER
	UNITS     "0.01 "
	ACCESS read-only
	STATUS mandatory
	DESCRIPTION
		"First_source_2_branch_67_output_power"
	::= { FirstGeneral_Precision_Distribution82Analog 867 }
First_source_2_branch_68_output_power OBJECT-TYPE
	SYNTAX INTEGER
	UNITS     "0.01 "
	ACCESS read-only
	STATUS mandatory
	DESCRIPTION
		"First_source_2_branch_68_output_power"
	::= { FirstGeneral_Precision_Distribution82Analog 868 }
First_source_2_branch_69_output_power OBJECT-TYPE
	SYNTAX INTEGER
	UNITS     "0.01 "
	ACCESS read-only
	STATUS mandatory
	DESCRIPTION
		"First_source_2_branch_69_output_power"
	::= { FirstGeneral_Precision_Distribution82Analog 869 }
First_source_2_branch_70_output_power OBJECT-TYPE
	SYNTAX INTEGER
	UNITS     "0.01 "
	ACCESS read-only
	STATUS mandatory
	DESCRIPTION
		"First_source_2_branch_70_output_power"
	::= { FirstGeneral_Precision_Distribution82Analog 870 }
First_source_2_branch_71_output_power OBJECT-TYPE
	SYNTAX INTEGER
	UNITS     "0.01 "
	ACCESS read-only
	STATUS mandatory
	DESCRIPTION
		"First_source_2_branch_71_output_power"
	::= { FirstGeneral_Precision_Distribution82Analog 871 }
First_source_2_branch_72_output_power OBJECT-TYPE
	SYNTAX INTEGER
	UNITS     "0.01 "
	ACCESS read-only
	STATUS mandatory
	DESCRIPTION
		"First_source_2_branch_72_output_power"
	::= { FirstGeneral_Precision_Distribution82Analog 872 }
First_source_2_branch_73_output_power OBJECT-TYPE
	SYNTAX INTEGER
	UNITS     "0.01 "
	ACCESS read-only
	STATUS mandatory
	DESCRIPTION
		"First_source_2_branch_73_output_power"
	::= { FirstGeneral_Precision_Distribution82Analog 873 }
First_source_2_branch_74_output_power OBJECT-TYPE
	SYNTAX INTEGER
	UNITS     "0.01 "
	ACCESS read-only
	STATUS mandatory
	DESCRIPTION
		"First_source_2_branch_74_output_power"
	::= { FirstGeneral_Precision_Distribution82Analog 874 }
First_source_2_branch_75_output_power OBJECT-TYPE
	SYNTAX INTEGER
	UNITS     "0.01 "
	ACCESS read-only
	STATUS mandatory
	DESCRIPTION
		"First_source_2_branch_75_output_power"
	::= { FirstGeneral_Precision_Distribution82Analog 875 }
First_source_2_branch_76_output_power OBJECT-TYPE
	SYNTAX INTEGER
	UNITS     "0.01 "
	ACCESS read-only
	STATUS mandatory
	DESCRIPTION
		"First_source_2_branch_76_output_power"
	::= { FirstGeneral_Precision_Distribution82Analog 876 }
First_source_2_branch_77_output_power OBJECT-TYPE
	SYNTAX INTEGER
	UNITS     "0.01 "
	ACCESS read-only
	STATUS mandatory
	DESCRIPTION
		"First_source_2_branch_77_output_power"
	::= { FirstGeneral_Precision_Distribution82Analog 877 }
First_source_2_branch_78_output_power OBJECT-TYPE
	SYNTAX INTEGER
	UNITS     "0.01 "
	ACCESS read-only
	STATUS mandatory
	DESCRIPTION
		"First_source_2_branch_78_output_power"
	::= { FirstGeneral_Precision_Distribution82Analog 878 }
First_source_2_branch_79_output_power OBJECT-TYPE
	SYNTAX INTEGER
	UNITS     "0.01 "
	ACCESS read-only
	STATUS mandatory
	DESCRIPTION
		"First_source_2_branch_79_output_power"
	::= { FirstGeneral_Precision_Distribution82Analog 879 }
First_source_2_branch_80_output_power OBJECT-TYPE
	SYNTAX INTEGER
	UNITS     "0.01 "
	ACCESS read-only
	STATUS mandatory
	DESCRIPTION
		"First_source_2_branch_80_output_power"
	::= { FirstGeneral_Precision_Distribution82Analog 880 }
First_source_2_branch_81_output_power OBJECT-TYPE
	SYNTAX INTEGER
	UNITS     "0.01 "
	ACCESS read-only
	STATUS mandatory
	DESCRIPTION
		"First_source_2_branch_81_output_power"
	::= { FirstGeneral_Precision_Distribution82Analog 881 }
First_source_2_branch_82_output_power OBJECT-TYPE
	SYNTAX INTEGER
	UNITS     "0.01 "
	ACCESS read-only
	STATUS mandatory
	DESCRIPTION
		"First_source_2_branch_82_output_power"
	::= { FirstGeneral_Precision_Distribution82Analog 882 }
First_source_2_branch_83_output_power OBJECT-TYPE
	SYNTAX INTEGER
	UNITS     "0.01 "
	ACCESS read-only
	STATUS mandatory
	DESCRIPTION
		"First_source_2_branch_83_output_power"
	::= { FirstGeneral_Precision_Distribution82Analog 883 }
First_source_2_branch_84_output_power OBJECT-TYPE
	SYNTAX INTEGER
	UNITS     "0.01 "
	ACCESS read-only
	STATUS mandatory
	DESCRIPTION
		"First_source_2_branch_84_output_power"
	::= { FirstGeneral_Precision_Distribution82Analog 884 }
First_source_2_branch_85_output_power OBJECT-TYPE
	SYNTAX INTEGER
	UNITS     "0.01 "
	ACCESS read-only
	STATUS mandatory
	DESCRIPTION
		"First_source_2_branch_85_output_power"
	::= { FirstGeneral_Precision_Distribution82Analog 885 }
First_source_2_branch_86_output_power OBJECT-TYPE
	SYNTAX INTEGER
	UNITS     "0.01 "
	ACCESS read-only
	STATUS mandatory
	DESCRIPTION
		"First_source_2_branch_86_output_power"
	::= { FirstGeneral_Precision_Distribution82Analog 886 }
First_source_2_branch_87_output_power OBJECT-TYPE
	SYNTAX INTEGER
	UNITS     "0.01 "
	ACCESS read-only
	STATUS mandatory
	DESCRIPTION
		"First_source_2_branch_87_output_power"
	::= { FirstGeneral_Precision_Distribution82Analog 887 }
First_source_2_branch_88_output_power OBJECT-TYPE
	SYNTAX INTEGER
	UNITS     "0.01 "
	ACCESS read-only
	STATUS mandatory
	DESCRIPTION
		"First_source_2_branch_88_output_power"
	::= { FirstGeneral_Precision_Distribution82Analog 888 }
First_source_2_branch_89_output_power OBJECT-TYPE
	SYNTAX INTEGER
	UNITS     "0.01 "
	ACCESS read-only
	STATUS mandatory
	DESCRIPTION
		"First_source_2_branch_89_output_power"
	::= { FirstGeneral_Precision_Distribution82Analog 889 }
First_source_2_branch_90_output_power OBJECT-TYPE
	SYNTAX INTEGER
	UNITS     "0.01 "
	ACCESS read-only
	STATUS mandatory
	DESCRIPTION
		"First_source_2_branch_90_output_power"
	::= { FirstGeneral_Precision_Distribution82Analog 890 }
First_source_2_branch_91_output_power OBJECT-TYPE
	SYNTAX INTEGER
	UNITS     "0.01 "
	ACCESS read-only
	STATUS mandatory
	DESCRIPTION
		"First_source_2_branch_91_output_power"
	::= { FirstGeneral_Precision_Distribution82Analog 891 }
First_source_2_branch_92_output_power OBJECT-TYPE
	SYNTAX INTEGER
	UNITS     "0.01 "
	ACCESS read-only
	STATUS mandatory
	DESCRIPTION
		"First_source_2_branch_92_output_power"
	::= { FirstGeneral_Precision_Distribution82Analog 892 }
First_source_2_branch_93_output_power OBJECT-TYPE
	SYNTAX INTEGER
	UNITS     "0.01 "
	ACCESS read-only
	STATUS mandatory
	DESCRIPTION
		"First_source_2_branch_93_output_power"
	::= { FirstGeneral_Precision_Distribution82Analog 893 }
First_source_2_branch_94_output_power OBJECT-TYPE
	SYNTAX INTEGER
	UNITS     "0.01 "
	ACCESS read-only
	STATUS mandatory
	DESCRIPTION
		"First_source_2_branch_94_output_power"
	::= { FirstGeneral_Precision_Distribution82Analog 894 }
First_source_2_branch_95_output_power OBJECT-TYPE
	SYNTAX INTEGER
	UNITS     "0.01 "
	ACCESS read-only
	STATUS mandatory
	DESCRIPTION
		"First_source_2_branch_95_output_power"
	::= { FirstGeneral_Precision_Distribution82Analog 895 }
First_source_2_branch_96_output_power OBJECT-TYPE
	SYNTAX INTEGER
	UNITS     "0.01 "
	ACCESS read-only
	STATUS mandatory
	DESCRIPTION
		"First_source_2_branch_96_output_power"
	::= { FirstGeneral_Precision_Distribution82Analog 896 }
First_source_2_branch_97_output_power OBJECT-TYPE
	SYNTAX INTEGER
	UNITS     "0.01 "
	ACCESS read-only
	STATUS mandatory
	DESCRIPTION
		"First_source_2_branch_97_output_power"
	::= { FirstGeneral_Precision_Distribution82Analog 897 }
First_source_2_branch_98_output_power OBJECT-TYPE
	SYNTAX INTEGER
	UNITS     "0.01 "
	ACCESS read-only
	STATUS mandatory
	DESCRIPTION
		"First_source_2_branch_98_output_power"
	::= { FirstGeneral_Precision_Distribution82Analog 898 }
First_source_2_branch_99_output_power OBJECT-TYPE
	SYNTAX INTEGER
	UNITS     "0.01 "
	ACCESS read-only
	STATUS mandatory
	DESCRIPTION
		"First_source_2_branch_99_output_power"
	::= { FirstGeneral_Precision_Distribution82Analog 899 }
First_source_2_branch_100_output_power OBJECT-TYPE
	SYNTAX INTEGER
	UNITS     "0.01 "
	ACCESS read-only
	STATUS mandatory
	DESCRIPTION
		"First_source_2_branch_100_output_power"
	::= { FirstGeneral_Precision_Distribution82Analog 900 }

-- the General_Precision_Distribution82Status group
--addGeneral_Precision_Distribution82Status

-- the General_Precision_Distribution82Alarm group
--addGeneral_Precision_Distribution82Alarm
First_Communication_Alarm OBJECT-TYPE
	SYNTAX INTEGER  {
		Normal(0),
		Alarm(1)
	}
	ACCESS read-only
	STATUS mandatory
	DESCRIPTION
		"First_Communication_Alarm"
	::= { FirstGeneral_Precision_Distribution82Alarm 1 }
First_I_Road_QF1_switch_status OBJECT-TYPE
	SYNTAX INTEGER  {
		Normal(0),
		Alarm(1)
	}
	ACCESS read-only
	STATUS mandatory
	DESCRIPTION
		"First_I_Road_QF1_switch_status"
	::= { FirstGeneral_Precision_Distribution82Alarm 2 }
First_I_Road_QF2_switch_status OBJECT-TYPE
	SYNTAX INTEGER  {
		Normal(0),
		Alarm(1)
	}
	ACCESS read-only
	STATUS mandatory
	DESCRIPTION
		"First_I_Road_QF2_switch_status"
	::= { FirstGeneral_Precision_Distribution82Alarm 3 }
First_I_Road_QF3_switch_status OBJECT-TYPE
	SYNTAX INTEGER  {
		Normal(0),
		Alarm(1)
	}
	ACCESS read-only
	STATUS mandatory
	DESCRIPTION
		"First_I_Road_QF3_switch_status"
	::= { FirstGeneral_Precision_Distribution82Alarm 4 }
First_I_Road_Lightning_Protection_switch_1_status OBJECT-TYPE
	SYNTAX INTEGER  {
		Normal(0),
		Alarm(1)
	}
	ACCESS read-only
	STATUS mandatory
	DESCRIPTION
		"First_I_Road_Lightning_Protection_switch_1_status"
	::= { FirstGeneral_Precision_Distribution82Alarm 5 }
First_I_Road_Lightning_Protection_Switch_2_status OBJECT-TYPE
	SYNTAX INTEGER  {
		Normal(0),
		Alarm(1)
	}
	ACCESS read-only
	STATUS mandatory
	DESCRIPTION
		"First_I_Road_Lightning_Protection_Switch_2_status"
	::= { FirstGeneral_Precision_Distribution82Alarm 6 }
First_I_Road_Lightning_Protection_Switch_3_status OBJECT-TYPE
	SYNTAX INTEGER  {
		Normal(0),
		Alarm(1)
	}
	ACCESS read-only
	STATUS mandatory
	DESCRIPTION
		"First_I_Road_Lightning_Protection_Switch_3_status"
	::= { FirstGeneral_Precision_Distribution82Alarm 7 }
First_I_Road_lightning_protection_Fault_alarm OBJECT-TYPE
	SYNTAX INTEGER  {
		Normal(0),
		Alarm(1)
	}
	ACCESS read-only
	STATUS mandatory
	DESCRIPTION
		"First_I_Road_lightning_protection_Fault_alarm"
	::= { FirstGeneral_Precision_Distribution82Alarm 8 }
First_I_Road_main_road_overvoltage_alarm OBJECT-TYPE
	SYNTAX INTEGER  {
		Normal(0),
		Alarm(1)
	}
	ACCESS read-only
	STATUS mandatory
	DESCRIPTION
		"First_I_Road_main_road_overvoltage_alarm"
	::= { FirstGeneral_Precision_Distribution82Alarm 9 }
First_I_Road_main_road_undervoltage_alarm OBJECT-TYPE
	SYNTAX INTEGER  {
		Normal(0),
		Alarm(1)
	}
	ACCESS read-only
	STATUS mandatory
	DESCRIPTION
		"First_I_Road_main_road_undervoltage_alarm"
	::= { FirstGeneral_Precision_Distribution82Alarm 10 }
First_I_Road_main_road_open_phase_alarm OBJECT-TYPE
	SYNTAX INTEGER  {
		Normal(0),
		Alarm(1)
	}
	ACCESS read-only
	STATUS mandatory
	DESCRIPTION
		"First_I_Road_main_road_open_phase_alarm"
	::= { FirstGeneral_Precision_Distribution82Alarm 11 }
First_I_Road_main_road_overcurrent_alarm OBJECT-TYPE
	SYNTAX INTEGER  {
		Normal(0),
		Alarm(1)
	}
	ACCESS read-only
	STATUS mandatory
	DESCRIPTION
		"First_I_Road_main_road_overcurrent_alarm"
	::= { FirstGeneral_Precision_Distribution82Alarm 12 }
First_I_Road_channel_frequency_overrun_alarm OBJECT-TYPE
	SYNTAX INTEGER  {
		Normal(0),
		Alarm(1)
	}
	ACCESS read-only
	STATUS mandatory
	DESCRIPTION
		"First_I_Road_channel_frequency_overrun_alarm"
	::= { FirstGeneral_Precision_Distribution82Alarm 13 }
First_I_Road_circuit_switch_abnormal_alarm OBJECT-TYPE
	SYNTAX INTEGER  {
		Normal(0),
		Alarm(1)
	}
	ACCESS read-only
	STATUS mandatory
	DESCRIPTION
		"First_I_Road_circuit_switch_abnormal_alarm"
	::= { FirstGeneral_Precision_Distribution82Alarm 14 }
First_II_Road_QF1_switch_status OBJECT-TYPE
	SYNTAX INTEGER  {
		Normal(0),
		Alarm(1)
	}
	ACCESS read-only
	STATUS mandatory
	DESCRIPTION
		"First_II_Road_QF1_switch_status"
	::= { FirstGeneral_Precision_Distribution82Alarm 15 }
First_II_Road_QF2_switch_status OBJECT-TYPE
	SYNTAX INTEGER  {
		Normal(0),
		Alarm(1)
	}
	ACCESS read-only
	STATUS mandatory
	DESCRIPTION
		"First_II_Road_QF2_switch_status"
	::= { FirstGeneral_Precision_Distribution82Alarm 16 }
First_II_Road_QF3_switch_status OBJECT-TYPE
	SYNTAX INTEGER  {
		Normal(0),
		Alarm(1)
	}
	ACCESS read-only
	STATUS mandatory
	DESCRIPTION
		"First_II_Road_QF3_switch_status"
	::= { FirstGeneral_Precision_Distribution82Alarm 17 }
First_II_Road_Lightning_Protection_switch_1_status OBJECT-TYPE
	SYNTAX INTEGER  {
		Normal(0),
		Alarm(1)
	}
	ACCESS read-only
	STATUS mandatory
	DESCRIPTION
		"First_II_Road_Lightning_Protection_switch_1_status"
	::= { FirstGeneral_Precision_Distribution82Alarm 18 }
First_II_Road_Lightning_Protection_Switch_2_status OBJECT-TYPE
	SYNTAX INTEGER  {
		Normal(0),
		Alarm(1)
	}
	ACCESS read-only
	STATUS mandatory
	DESCRIPTION
		"First_II_Road_Lightning_Protection_Switch_2_status"
	::= { FirstGeneral_Precision_Distribution82Alarm 19 }
First_II_Road_Lightning_Protection_Switch_3_status OBJECT-TYPE
	SYNTAX INTEGER  {
		Normal(0),
		Alarm(1)
	}
	ACCESS read-only
	STATUS mandatory
	DESCRIPTION
		"First_II_Road_Lightning_Protection_Switch_3_status"
	::= { FirstGeneral_Precision_Distribution82Alarm 20 }
First_II_Road_lightning_protection_Fault_alarm OBJECT-TYPE
	SYNTAX INTEGER  {
		Normal(0),
		Alarm(1)
	}
	ACCESS read-only
	STATUS mandatory
	DESCRIPTION
		"First_II_Road_lightning_protection_Fault_alarm"
	::= { FirstGeneral_Precision_Distribution82Alarm 21 }
First_II_Road_main_road_overvoltage_alarm OBJECT-TYPE
	SYNTAX INTEGER  {
		Normal(0),
		Alarm(1)
	}
	ACCESS read-only
	STATUS mandatory
	DESCRIPTION
		"First_II_Road_main_road_overvoltage_alarm"
	::= { FirstGeneral_Precision_Distribution82Alarm 22 }
First_II_Road_main_road_undervoltage_alarm OBJECT-TYPE
	SYNTAX INTEGER  {
		Normal(0),
		Alarm(1)
	}
	ACCESS read-only
	STATUS mandatory
	DESCRIPTION
		"First_II_Road_main_road_undervoltage_alarm"
	::= { FirstGeneral_Precision_Distribution82Alarm 23 }
First_II_Road_main_road_open_phase_alarm OBJECT-TYPE
	SYNTAX INTEGER  {
		Normal(0),
		Alarm(1)
	}
	ACCESS read-only
	STATUS mandatory
	DESCRIPTION
		"First_II_Road_main_road_open_phase_alarm"
	::= { FirstGeneral_Precision_Distribution82Alarm 24 }
First_II_Road_main_road_overcurrent_alarm OBJECT-TYPE
	SYNTAX INTEGER  {
		Normal(0),
		Alarm(1)
	}
	ACCESS read-only
	STATUS mandatory
	DESCRIPTION
		"First_II_Road_main_road_overcurrent_alarm"
	::= { FirstGeneral_Precision_Distribution82Alarm 25 }
First_II_Road_channel_frequency_overrun_alarm OBJECT-TYPE
	SYNTAX INTEGER  {
		Normal(0),
		Alarm(1)
	}
	ACCESS read-only
	STATUS mandatory
	DESCRIPTION
		"First_II_Road_channel_frequency_overrun_alarm"
	::= { FirstGeneral_Precision_Distribution82Alarm 26 }
First_II_Road_circuit_switch_abnormal_alarm OBJECT-TYPE
	SYNTAX INTEGER  {
		Normal(0),
		Alarm(1)
	}
	ACCESS read-only
	STATUS mandatory
	DESCRIPTION
		"First_II_Road_circuit_switch_abnormal_alarm"
	::= { FirstGeneral_Precision_Distribution82Alarm 27 }
First_source_1_branch_1_output_switch_status OBJECT-TYPE
	SYNTAX INTEGER  {
		Normal(0),
		Alarm(1)
	}
	ACCESS read-only
	STATUS mandatory
	DESCRIPTION
		"First_source_1_branch_1_output_switch_status"
	::= { FirstGeneral_Precision_Distribution82Alarm 28 }
First_source_1_branch_2_output_switch_status OBJECT-TYPE
	SYNTAX INTEGER  {
		Normal(0),
		Alarm(1)
	}
	ACCESS read-only
	STATUS mandatory
	DESCRIPTION
		"First_source_1_branch_2_output_switch_status"
	::= { FirstGeneral_Precision_Distribution82Alarm 29 }
First_source_1_branch_3_output_switch_status OBJECT-TYPE
	SYNTAX INTEGER  {
		Normal(0),
		Alarm(1)
	}
	ACCESS read-only
	STATUS mandatory
	DESCRIPTION
		"First_source_1_branch_3_output_switch_status"
	::= { FirstGeneral_Precision_Distribution82Alarm 30 }
First_source_1_branch_4_output_switch_status OBJECT-TYPE
	SYNTAX INTEGER  {
		Normal(0),
		Alarm(1)
	}
	ACCESS read-only
	STATUS mandatory
	DESCRIPTION
		"First_source_1_branch_4_output_switch_status"
	::= { FirstGeneral_Precision_Distribution82Alarm 31 }
First_source_1_branch_5_output_switch_status OBJECT-TYPE
	SYNTAX INTEGER  {
		Normal(0),
		Alarm(1)
	}
	ACCESS read-only
	STATUS mandatory
	DESCRIPTION
		"First_source_1_branch_5_output_switch_status"
	::= { FirstGeneral_Precision_Distribution82Alarm 32 }
First_source_1_branch_6_output_switch_status OBJECT-TYPE
	SYNTAX INTEGER  {
		Normal(0),
		Alarm(1)
	}
	ACCESS read-only
	STATUS mandatory
	DESCRIPTION
		"First_source_1_branch_6_output_switch_status"
	::= { FirstGeneral_Precision_Distribution82Alarm 33 }
First_source_1_branch_7_output_switch_status OBJECT-TYPE
	SYNTAX INTEGER  {
		Normal(0),
		Alarm(1)
	}
	ACCESS read-only
	STATUS mandatory
	DESCRIPTION
		"First_source_1_branch_7_output_switch_status"
	::= { FirstGeneral_Precision_Distribution82Alarm 34 }
First_source_1_branch_8_output_switch_status OBJECT-TYPE
	SYNTAX INTEGER  {
		Normal(0),
		Alarm(1)
	}
	ACCESS read-only
	STATUS mandatory
	DESCRIPTION
		"First_source_1_branch_8_output_switch_status"
	::= { FirstGeneral_Precision_Distribution82Alarm 35 }
First_source_1_branch_9_output_switch_status OBJECT-TYPE
	SYNTAX INTEGER  {
		Normal(0),
		Alarm(1)
	}
	ACCESS read-only
	STATUS mandatory
	DESCRIPTION
		"First_source_1_branch_9_output_switch_status"
	::= { FirstGeneral_Precision_Distribution82Alarm 36 }
First_source_1_branch_10_output_switch_status OBJECT-TYPE
	SYNTAX INTEGER  {
		Normal(0),
		Alarm(1)
	}
	ACCESS read-only
	STATUS mandatory
	DESCRIPTION
		"First_source_1_branch_10_output_switch_status"
	::= { FirstGeneral_Precision_Distribution82Alarm 37 }
First_source_1_branch_11_output_switch_status OBJECT-TYPE
	SYNTAX INTEGER  {
		Normal(0),
		Alarm(1)
	}
	ACCESS read-only
	STATUS mandatory
	DESCRIPTION
		"First_source_1_branch_11_output_switch_status"
	::= { FirstGeneral_Precision_Distribution82Alarm 38 }
First_source_1_branch_12_output_switch_status OBJECT-TYPE
	SYNTAX INTEGER  {
		Normal(0),
		Alarm(1)
	}
	ACCESS read-only
	STATUS mandatory
	DESCRIPTION
		"First_source_1_branch_12_output_switch_status"
	::= { FirstGeneral_Precision_Distribution82Alarm 39 }
First_source_1_branch_13_output_switch_status OBJECT-TYPE
	SYNTAX INTEGER  {
		Normal(0),
		Alarm(1)
	}
	ACCESS read-only
	STATUS mandatory
	DESCRIPTION
		"First_source_1_branch_13_output_switch_status"
	::= { FirstGeneral_Precision_Distribution82Alarm 40 }
First_source_1_branch_14_output_switch_status OBJECT-TYPE
	SYNTAX INTEGER  {
		Normal(0),
		Alarm(1)
	}
	ACCESS read-only
	STATUS mandatory
	DESCRIPTION
		"First_source_1_branch_14_output_switch_status"
	::= { FirstGeneral_Precision_Distribution82Alarm 41 }
First_source_1_branch_15_output_switch_status OBJECT-TYPE
	SYNTAX INTEGER  {
		Normal(0),
		Alarm(1)
	}
	ACCESS read-only
	STATUS mandatory
	DESCRIPTION
		"First_source_1_branch_15_output_switch_status"
	::= { FirstGeneral_Precision_Distribution82Alarm 42 }
First_source_1_branch_16_output_switch_status OBJECT-TYPE
	SYNTAX INTEGER  {
		Normal(0),
		Alarm(1)
	}
	ACCESS read-only
	STATUS mandatory
	DESCRIPTION
		"First_source_1_branch_16_output_switch_status"
	::= { FirstGeneral_Precision_Distribution82Alarm 43 }
First_source_1_branch_17_output_switch_status OBJECT-TYPE
	SYNTAX INTEGER  {
		Normal(0),
		Alarm(1)
	}
	ACCESS read-only
	STATUS mandatory
	DESCRIPTION
		"First_source_1_branch_17_output_switch_status"
	::= { FirstGeneral_Precision_Distribution82Alarm 44 }
First_source_1_branch_18_output_switch_status OBJECT-TYPE
	SYNTAX INTEGER  {
		Normal(0),
		Alarm(1)
	}
	ACCESS read-only
	STATUS mandatory
	DESCRIPTION
		"First_source_1_branch_18_output_switch_status"
	::= { FirstGeneral_Precision_Distribution82Alarm 45 }
First_source_1_branch_19_output_switch_status OBJECT-TYPE
	SYNTAX INTEGER  {
		Normal(0),
		Alarm(1)
	}
	ACCESS read-only
	STATUS mandatory
	DESCRIPTION
		"First_source_1_branch_19_output_switch_status"
	::= { FirstGeneral_Precision_Distribution82Alarm 46 }
First_source_1_branch_20_output_switch_status OBJECT-TYPE
	SYNTAX INTEGER  {
		Normal(0),
		Alarm(1)
	}
	ACCESS read-only
	STATUS mandatory
	DESCRIPTION
		"First_source_1_branch_20_output_switch_status"
	::= { FirstGeneral_Precision_Distribution82Alarm 47 }
First_source_1_branch_21_output_switch_status OBJECT-TYPE
	SYNTAX INTEGER  {
		Normal(0),
		Alarm(1)
	}
	ACCESS read-only
	STATUS mandatory
	DESCRIPTION
		"First_source_1_branch_21_output_switch_status"
	::= { FirstGeneral_Precision_Distribution82Alarm 48 }
First_source_1_branch_22_output_switch_status OBJECT-TYPE
	SYNTAX INTEGER  {
		Normal(0),
		Alarm(1)
	}
	ACCESS read-only
	STATUS mandatory
	DESCRIPTION
		"First_source_1_branch_22_output_switch_status"
	::= { FirstGeneral_Precision_Distribution82Alarm 49 }
First_source_1_branch_23_output_switch_status OBJECT-TYPE
	SYNTAX INTEGER  {
		Normal(0),
		Alarm(1)
	}
	ACCESS read-only
	STATUS mandatory
	DESCRIPTION
		"First_source_1_branch_23_output_switch_status"
	::= { FirstGeneral_Precision_Distribution82Alarm 50 }
First_source_1_branch_24_output_switch_status OBJECT-TYPE
	SYNTAX INTEGER  {
		Normal(0),
		Alarm(1)
	}
	ACCESS read-only
	STATUS mandatory
	DESCRIPTION
		"First_source_1_branch_24_output_switch_status"
	::= { FirstGeneral_Precision_Distribution82Alarm 51 }
First_source_1_branch_25_output_switch_status OBJECT-TYPE
	SYNTAX INTEGER  {
		Normal(0),
		Alarm(1)
	}
	ACCESS read-only
	STATUS mandatory
	DESCRIPTION
		"First_source_1_branch_25_output_switch_status"
	::= { FirstGeneral_Precision_Distribution82Alarm 52 }
First_source_1_branch_26_output_switch_status OBJECT-TYPE
	SYNTAX INTEGER  {
		Normal(0),
		Alarm(1)
	}
	ACCESS read-only
	STATUS mandatory
	DESCRIPTION
		"First_source_1_branch_26_output_switch_status"
	::= { FirstGeneral_Precision_Distribution82Alarm 53 }
First_source_1_branch_27_output_switch_status OBJECT-TYPE
	SYNTAX INTEGER  {
		Normal(0),
		Alarm(1)
	}
	ACCESS read-only
	STATUS mandatory
	DESCRIPTION
		"First_source_1_branch_27_output_switch_status"
	::= { FirstGeneral_Precision_Distribution82Alarm 54 }
First_source_1_branch_28_output_switch_status OBJECT-TYPE
	SYNTAX INTEGER  {
		Normal(0),
		Alarm(1)
	}
	ACCESS read-only
	STATUS mandatory
	DESCRIPTION
		"First_source_1_branch_28_output_switch_status"
	::= { FirstGeneral_Precision_Distribution82Alarm 55 }
First_source_1_branch_29_output_switch_status OBJECT-TYPE
	SYNTAX INTEGER  {
		Normal(0),
		Alarm(1)
	}
	ACCESS read-only
	STATUS mandatory
	DESCRIPTION
		"First_source_1_branch_29_output_switch_status"
	::= { FirstGeneral_Precision_Distribution82Alarm 56 }
First_source_1_branch_30_output_switch_status OBJECT-TYPE
	SYNTAX INTEGER  {
		Normal(0),
		Alarm(1)
	}
	ACCESS read-only
	STATUS mandatory
	DESCRIPTION
		"First_source_1_branch_30_output_switch_status"
	::= { FirstGeneral_Precision_Distribution82Alarm 57 }
First_source_1_branch_31_output_switch_status OBJECT-TYPE
	SYNTAX INTEGER  {
		Normal(0),
		Alarm(1)
	}
	ACCESS read-only
	STATUS mandatory
	DESCRIPTION
		"First_source_1_branch_31_output_switch_status"
	::= { FirstGeneral_Precision_Distribution82Alarm 58 }
First_source_1_branch_32_output_switch_status OBJECT-TYPE
	SYNTAX INTEGER  {
		Normal(0),
		Alarm(1)
	}
	ACCESS read-only
	STATUS mandatory
	DESCRIPTION
		"First_source_1_branch_32_output_switch_status"
	::= { FirstGeneral_Precision_Distribution82Alarm 59 }
First_source_1_branch_33_output_switch_status OBJECT-TYPE
	SYNTAX INTEGER  {
		Normal(0),
		Alarm(1)
	}
	ACCESS read-only
	STATUS mandatory
	DESCRIPTION
		"First_source_1_branch_33_output_switch_status"
	::= { FirstGeneral_Precision_Distribution82Alarm 60 }
First_source_1_branch_34_output_switch_status OBJECT-TYPE
	SYNTAX INTEGER  {
		Normal(0),
		Alarm(1)
	}
	ACCESS read-only
	STATUS mandatory
	DESCRIPTION
		"First_source_1_branch_34_output_switch_status"
	::= { FirstGeneral_Precision_Distribution82Alarm 61 }
First_source_1_branch_35_output_switch_status OBJECT-TYPE
	SYNTAX INTEGER  {
		Normal(0),
		Alarm(1)
	}
	ACCESS read-only
	STATUS mandatory
	DESCRIPTION
		"First_source_1_branch_35_output_switch_status"
	::= { FirstGeneral_Precision_Distribution82Alarm 62 }
First_source_1_branch_36_output_switch_status OBJECT-TYPE
	SYNTAX INTEGER  {
		Normal(0),
		Alarm(1)
	}
	ACCESS read-only
	STATUS mandatory
	DESCRIPTION
		"First_source_1_branch_36_output_switch_status"
	::= { FirstGeneral_Precision_Distribution82Alarm 63 }
First_source_1_branch_37_output_switch_status OBJECT-TYPE
	SYNTAX INTEGER  {
		Normal(0),
		Alarm(1)
	}
	ACCESS read-only
	STATUS mandatory
	DESCRIPTION
		"First_source_1_branch_37_output_switch_status"
	::= { FirstGeneral_Precision_Distribution82Alarm 64 }
First_source_1_branch_38_output_switch_status OBJECT-TYPE
	SYNTAX INTEGER  {
		Normal(0),
		Alarm(1)
	}
	ACCESS read-only
	STATUS mandatory
	DESCRIPTION
		"First_source_1_branch_38_output_switch_status"
	::= { FirstGeneral_Precision_Distribution82Alarm 65 }
First_source_1_branch_39_output_switch_status OBJECT-TYPE
	SYNTAX INTEGER  {
		Normal(0),
		Alarm(1)
	}
	ACCESS read-only
	STATUS mandatory
	DESCRIPTION
		"First_source_1_branch_39_output_switch_status"
	::= { FirstGeneral_Precision_Distribution82Alarm 66 }
First_source_1_branch_40_output_switch_status OBJECT-TYPE
	SYNTAX INTEGER  {
		Normal(0),
		Alarm(1)
	}
	ACCESS read-only
	STATUS mandatory
	DESCRIPTION
		"First_source_1_branch_40_output_switch_status"
	::= { FirstGeneral_Precision_Distribution82Alarm 67 }
First_source_1_branch_41_output_switch_status OBJECT-TYPE
	SYNTAX INTEGER  {
		Normal(0),
		Alarm(1)
	}
	ACCESS read-only
	STATUS mandatory
	DESCRIPTION
		"First_source_1_branch_41_output_switch_status"
	::= { FirstGeneral_Precision_Distribution82Alarm 68 }
First_source_1_branch_42_output_switch_status OBJECT-TYPE
	SYNTAX INTEGER  {
		Normal(0),
		Alarm(1)
	}
	ACCESS read-only
	STATUS mandatory
	DESCRIPTION
		"First_source_1_branch_42_output_switch_status"
	::= { FirstGeneral_Precision_Distribution82Alarm 69 }
First_source_1_branch_43_output_switch_status OBJECT-TYPE
	SYNTAX INTEGER  {
		Normal(0),
		Alarm(1)
	}
	ACCESS read-only
	STATUS mandatory
	DESCRIPTION
		"First_source_1_branch_43_output_switch_status"
	::= { FirstGeneral_Precision_Distribution82Alarm 70 }
First_source_1_branch_44_output_switch_status OBJECT-TYPE
	SYNTAX INTEGER  {
		Normal(0),
		Alarm(1)
	}
	ACCESS read-only
	STATUS mandatory
	DESCRIPTION
		"First_source_1_branch_44_output_switch_status"
	::= { FirstGeneral_Precision_Distribution82Alarm 71 }
First_source_1_branch_45_output_switch_status OBJECT-TYPE
	SYNTAX INTEGER  {
		Normal(0),
		Alarm(1)
	}
	ACCESS read-only
	STATUS mandatory
	DESCRIPTION
		"First_source_1_branch_45_output_switch_status"
	::= { FirstGeneral_Precision_Distribution82Alarm 72 }
First_source_1_branch_46_output_switch_status OBJECT-TYPE
	SYNTAX INTEGER  {
		Normal(0),
		Alarm(1)
	}
	ACCESS read-only
	STATUS mandatory
	DESCRIPTION
		"First_source_1_branch_46_output_switch_status"
	::= { FirstGeneral_Precision_Distribution82Alarm 73 }
First_source_1_branch_47_output_switch_status OBJECT-TYPE
	SYNTAX INTEGER  {
		Normal(0),
		Alarm(1)
	}
	ACCESS read-only
	STATUS mandatory
	DESCRIPTION
		"First_source_1_branch_47_output_switch_status"
	::= { FirstGeneral_Precision_Distribution82Alarm 74 }
First_source_1_branch_48_output_switch_status OBJECT-TYPE
	SYNTAX INTEGER  {
		Normal(0),
		Alarm(1)
	}
	ACCESS read-only
	STATUS mandatory
	DESCRIPTION
		"First_source_1_branch_48_output_switch_status"
	::= { FirstGeneral_Precision_Distribution82Alarm 75 }
First_source_1_branch_49_output_switch_status OBJECT-TYPE
	SYNTAX INTEGER  {
		Normal(0),
		Alarm(1)
	}
	ACCESS read-only
	STATUS mandatory
	DESCRIPTION
		"First_source_1_branch_49_output_switch_status"
	::= { FirstGeneral_Precision_Distribution82Alarm 76 }
First_source_1_branch_50_output_switch_status OBJECT-TYPE
	SYNTAX INTEGER  {
		Normal(0),
		Alarm(1)
	}
	ACCESS read-only
	STATUS mandatory
	DESCRIPTION
		"First_source_1_branch_50_output_switch_status"
	::= { FirstGeneral_Precision_Distribution82Alarm 77 }
First_source_1_branch_51_output_switch_status OBJECT-TYPE
	SYNTAX INTEGER  {
		Normal(0),
		Alarm(1)
	}
	ACCESS read-only
	STATUS mandatory
	DESCRIPTION
		"First_source_1_branch_51_output_switch_status"
	::= { FirstGeneral_Precision_Distribution82Alarm 78 }
First_source_1_branch_52_output_switch_status OBJECT-TYPE
	SYNTAX INTEGER  {
		Normal(0),
		Alarm(1)
	}
	ACCESS read-only
	STATUS mandatory
	DESCRIPTION
		"First_source_1_branch_52_output_switch_status"
	::= { FirstGeneral_Precision_Distribution82Alarm 79 }
First_source_1_branch_53_output_switch_status OBJECT-TYPE
	SYNTAX INTEGER  {
		Normal(0),
		Alarm(1)
	}
	ACCESS read-only
	STATUS mandatory
	DESCRIPTION
		"First_source_1_branch_53_output_switch_status"
	::= { FirstGeneral_Precision_Distribution82Alarm 80 }
First_source_1_branch_54_output_switch_status OBJECT-TYPE
	SYNTAX INTEGER  {
		Normal(0),
		Alarm(1)
	}
	ACCESS read-only
	STATUS mandatory
	DESCRIPTION
		"First_source_1_branch_54_output_switch_status"
	::= { FirstGeneral_Precision_Distribution82Alarm 81 }
First_source_1_branch_55_output_switch_status OBJECT-TYPE
	SYNTAX INTEGER  {
		Normal(0),
		Alarm(1)
	}
	ACCESS read-only
	STATUS mandatory
	DESCRIPTION
		"First_source_1_branch_55_output_switch_status"
	::= { FirstGeneral_Precision_Distribution82Alarm 82 }
First_source_1_branch_56_output_switch_status OBJECT-TYPE
	SYNTAX INTEGER  {
		Normal(0),
		Alarm(1)
	}
	ACCESS read-only
	STATUS mandatory
	DESCRIPTION
		"First_source_1_branch_56_output_switch_status"
	::= { FirstGeneral_Precision_Distribution82Alarm 83 }
First_source_1_branch_57_output_switch_status OBJECT-TYPE
	SYNTAX INTEGER  {
		Normal(0),
		Alarm(1)
	}
	ACCESS read-only
	STATUS mandatory
	DESCRIPTION
		"First_source_1_branch_57_output_switch_status"
	::= { FirstGeneral_Precision_Distribution82Alarm 84 }
First_source_1_branch_58_output_switch_status OBJECT-TYPE
	SYNTAX INTEGER  {
		Normal(0),
		Alarm(1)
	}
	ACCESS read-only
	STATUS mandatory
	DESCRIPTION
		"First_source_1_branch_58_output_switch_status"
	::= { FirstGeneral_Precision_Distribution82Alarm 85 }
First_source_1_branch_59_output_switch_status OBJECT-TYPE
	SYNTAX INTEGER  {
		Normal(0),
		Alarm(1)
	}
	ACCESS read-only
	STATUS mandatory
	DESCRIPTION
		"First_source_1_branch_59_output_switch_status"
	::= { FirstGeneral_Precision_Distribution82Alarm 86 }
First_source_1_branch_60_output_switch_status OBJECT-TYPE
	SYNTAX INTEGER  {
		Normal(0),
		Alarm(1)
	}
	ACCESS read-only
	STATUS mandatory
	DESCRIPTION
		"First_source_1_branch_60_output_switch_status"
	::= { FirstGeneral_Precision_Distribution82Alarm 87 }
First_source_1_branch_61_output_switch_status OBJECT-TYPE
	SYNTAX INTEGER  {
		Normal(0),
		Alarm(1)
	}
	ACCESS read-only
	STATUS mandatory
	DESCRIPTION
		"First_source_1_branch_61_output_switch_status"
	::= { FirstGeneral_Precision_Distribution82Alarm 88 }
First_source_1_branch_62_output_switch_status OBJECT-TYPE
	SYNTAX INTEGER  {
		Normal(0),
		Alarm(1)
	}
	ACCESS read-only
	STATUS mandatory
	DESCRIPTION
		"First_source_1_branch_62_output_switch_status"
	::= { FirstGeneral_Precision_Distribution82Alarm 89 }
First_source_1_branch_63_output_switch_status OBJECT-TYPE
	SYNTAX INTEGER  {
		Normal(0),
		Alarm(1)
	}
	ACCESS read-only
	STATUS mandatory
	DESCRIPTION
		"First_source_1_branch_63_output_switch_status"
	::= { FirstGeneral_Precision_Distribution82Alarm 90 }
First_source_1_branch_64_output_switch_status OBJECT-TYPE
	SYNTAX INTEGER  {
		Normal(0),
		Alarm(1)
	}
	ACCESS read-only
	STATUS mandatory
	DESCRIPTION
		"First_source_1_branch_64_output_switch_status"
	::= { FirstGeneral_Precision_Distribution82Alarm 91 }
First_source_1_branch_65_output_switch_status OBJECT-TYPE
	SYNTAX INTEGER  {
		Normal(0),
		Alarm(1)
	}
	ACCESS read-only
	STATUS mandatory
	DESCRIPTION
		"First_source_1_branch_65_output_switch_status"
	::= { FirstGeneral_Precision_Distribution82Alarm 92 }
First_source_1_branch_66_output_switch_status OBJECT-TYPE
	SYNTAX INTEGER  {
		Normal(0),
		Alarm(1)
	}
	ACCESS read-only
	STATUS mandatory
	DESCRIPTION
		"First_source_1_branch_66_output_switch_status"
	::= { FirstGeneral_Precision_Distribution82Alarm 93 }
First_source_1_branch_67_output_switch_status OBJECT-TYPE
	SYNTAX INTEGER  {
		Normal(0),
		Alarm(1)
	}
	ACCESS read-only
	STATUS mandatory
	DESCRIPTION
		"First_source_1_branch_67_output_switch_status"
	::= { FirstGeneral_Precision_Distribution82Alarm 94 }
First_source_1_branch_68_output_switch_status OBJECT-TYPE
	SYNTAX INTEGER  {
		Normal(0),
		Alarm(1)
	}
	ACCESS read-only
	STATUS mandatory
	DESCRIPTION
		"First_source_1_branch_68_output_switch_status"
	::= { FirstGeneral_Precision_Distribution82Alarm 95 }
First_source_1_branch_69_output_switch_status OBJECT-TYPE
	SYNTAX INTEGER  {
		Normal(0),
		Alarm(1)
	}
	ACCESS read-only
	STATUS mandatory
	DESCRIPTION
		"First_source_1_branch_69_output_switch_status"
	::= { FirstGeneral_Precision_Distribution82Alarm 96 }
First_source_1_branch_70_output_switch_status OBJECT-TYPE
	SYNTAX INTEGER  {
		Normal(0),
		Alarm(1)
	}
	ACCESS read-only
	STATUS mandatory
	DESCRIPTION
		"First_source_1_branch_70_output_switch_status"
	::= { FirstGeneral_Precision_Distribution82Alarm 97 }
First_source_1_branch_71_output_switch_status OBJECT-TYPE
	SYNTAX INTEGER  {
		Normal(0),
		Alarm(1)
	}
	ACCESS read-only
	STATUS mandatory
	DESCRIPTION
		"First_source_1_branch_71_output_switch_status"
	::= { FirstGeneral_Precision_Distribution82Alarm 98 }
First_source_1_branch_72_output_switch_status OBJECT-TYPE
	SYNTAX INTEGER  {
		Normal(0),
		Alarm(1)
	}
	ACCESS read-only
	STATUS mandatory
	DESCRIPTION
		"First_source_1_branch_72_output_switch_status"
	::= { FirstGeneral_Precision_Distribution82Alarm 99 }
First_source_1_branch_73_output_switch_status OBJECT-TYPE
	SYNTAX INTEGER  {
		Normal(0),
		Alarm(1)
	}
	ACCESS read-only
	STATUS mandatory
	DESCRIPTION
		"First_source_1_branch_73_output_switch_status"
	::= { FirstGeneral_Precision_Distribution82Alarm 100 }
First_source_1_branch_74_output_switch_status OBJECT-TYPE
	SYNTAX INTEGER  {
		Normal(0),
		Alarm(1)
	}
	ACCESS read-only
	STATUS mandatory
	DESCRIPTION
		"First_source_1_branch_74_output_switch_status"
	::= { FirstGeneral_Precision_Distribution82Alarm 101 }
First_source_1_branch_75_output_switch_status OBJECT-TYPE
	SYNTAX INTEGER  {
		Normal(0),
		Alarm(1)
	}
	ACCESS read-only
	STATUS mandatory
	DESCRIPTION
		"First_source_1_branch_75_output_switch_status"
	::= { FirstGeneral_Precision_Distribution82Alarm 102 }
First_source_1_branch_76_output_switch_status OBJECT-TYPE
	SYNTAX INTEGER  {
		Normal(0),
		Alarm(1)
	}
	ACCESS read-only
	STATUS mandatory
	DESCRIPTION
		"First_source_1_branch_76_output_switch_status"
	::= { FirstGeneral_Precision_Distribution82Alarm 103 }
First_source_1_branch_77_output_switch_status OBJECT-TYPE
	SYNTAX INTEGER  {
		Normal(0),
		Alarm(1)
	}
	ACCESS read-only
	STATUS mandatory
	DESCRIPTION
		"First_source_1_branch_77_output_switch_status"
	::= { FirstGeneral_Precision_Distribution82Alarm 104 }
First_source_1_branch_78_output_switch_status OBJECT-TYPE
	SYNTAX INTEGER  {
		Normal(0),
		Alarm(1)
	}
	ACCESS read-only
	STATUS mandatory
	DESCRIPTION
		"First_source_1_branch_78_output_switch_status"
	::= { FirstGeneral_Precision_Distribution82Alarm 105 }
First_source_1_branch_79_output_switch_status OBJECT-TYPE
	SYNTAX INTEGER  {
		Normal(0),
		Alarm(1)
	}
	ACCESS read-only
	STATUS mandatory
	DESCRIPTION
		"First_source_1_branch_79_output_switch_status"
	::= { FirstGeneral_Precision_Distribution82Alarm 106 }
First_source_1_branch_80_output_switch_status OBJECT-TYPE
	SYNTAX INTEGER  {
		Normal(0),
		Alarm(1)
	}
	ACCESS read-only
	STATUS mandatory
	DESCRIPTION
		"First_source_1_branch_80_output_switch_status"
	::= { FirstGeneral_Precision_Distribution82Alarm 107 }
First_source_1_branch_81_output_switch_status OBJECT-TYPE
	SYNTAX INTEGER  {
		Normal(0),
		Alarm(1)
	}
	ACCESS read-only
	STATUS mandatory
	DESCRIPTION
		"First_source_1_branch_81_output_switch_status"
	::= { FirstGeneral_Precision_Distribution82Alarm 108 }
First_source_1_branch_82_output_switch_status OBJECT-TYPE
	SYNTAX INTEGER  {
		Normal(0),
		Alarm(1)
	}
	ACCESS read-only
	STATUS mandatory
	DESCRIPTION
		"First_source_1_branch_82_output_switch_status"
	::= { FirstGeneral_Precision_Distribution82Alarm 109 }
First_source_1_branch_83_output_switch_status OBJECT-TYPE
	SYNTAX INTEGER  {
		Normal(0),
		Alarm(1)
	}
	ACCESS read-only
	STATUS mandatory
	DESCRIPTION
		"First_source_1_branch_83_output_switch_status"
	::= { FirstGeneral_Precision_Distribution82Alarm 110 }
First_source_1_branch_84_output_switch_status OBJECT-TYPE
	SYNTAX INTEGER  {
		Normal(0),
		Alarm(1)
	}
	ACCESS read-only
	STATUS mandatory
	DESCRIPTION
		"First_source_1_branch_84_output_switch_status"
	::= { FirstGeneral_Precision_Distribution82Alarm 111 }
First_source_1_branch_85_output_switch_status OBJECT-TYPE
	SYNTAX INTEGER  {
		Normal(0),
		Alarm(1)
	}
	ACCESS read-only
	STATUS mandatory
	DESCRIPTION
		"First_source_1_branch_85_output_switch_status"
	::= { FirstGeneral_Precision_Distribution82Alarm 112 }
First_source_1_branch_86_output_switch_status OBJECT-TYPE
	SYNTAX INTEGER  {
		Normal(0),
		Alarm(1)
	}
	ACCESS read-only
	STATUS mandatory
	DESCRIPTION
		"First_source_1_branch_86_output_switch_status"
	::= { FirstGeneral_Precision_Distribution82Alarm 113 }
First_source_1_branch_87_output_switch_status OBJECT-TYPE
	SYNTAX INTEGER  {
		Normal(0),
		Alarm(1)
	}
	ACCESS read-only
	STATUS mandatory
	DESCRIPTION
		"First_source_1_branch_87_output_switch_status"
	::= { FirstGeneral_Precision_Distribution82Alarm 114 }
First_source_1_branch_88_output_switch_status OBJECT-TYPE
	SYNTAX INTEGER  {
		Normal(0),
		Alarm(1)
	}
	ACCESS read-only
	STATUS mandatory
	DESCRIPTION
		"First_source_1_branch_88_output_switch_status"
	::= { FirstGeneral_Precision_Distribution82Alarm 115 }
First_source_1_branch_89_output_switch_status OBJECT-TYPE
	SYNTAX INTEGER  {
		Normal(0),
		Alarm(1)
	}
	ACCESS read-only
	STATUS mandatory
	DESCRIPTION
		"First_source_1_branch_89_output_switch_status"
	::= { FirstGeneral_Precision_Distribution82Alarm 116 }
First_source_1_branch_90_output_switch_status OBJECT-TYPE
	SYNTAX INTEGER  {
		Normal(0),
		Alarm(1)
	}
	ACCESS read-only
	STATUS mandatory
	DESCRIPTION
		"First_source_1_branch_90_output_switch_status"
	::= { FirstGeneral_Precision_Distribution82Alarm 117 }
First_source_1_branch_91_output_switch_status OBJECT-TYPE
	SYNTAX INTEGER  {
		Normal(0),
		Alarm(1)
	}
	ACCESS read-only
	STATUS mandatory
	DESCRIPTION
		"First_source_1_branch_91_output_switch_status"
	::= { FirstGeneral_Precision_Distribution82Alarm 118 }
First_source_1_branch_92_output_switch_status OBJECT-TYPE
	SYNTAX INTEGER  {
		Normal(0),
		Alarm(1)
	}
	ACCESS read-only
	STATUS mandatory
	DESCRIPTION
		"First_source_1_branch_92_output_switch_status"
	::= { FirstGeneral_Precision_Distribution82Alarm 119 }
First_source_1_branch_93_output_switch_status OBJECT-TYPE
	SYNTAX INTEGER  {
		Normal(0),
		Alarm(1)
	}
	ACCESS read-only
	STATUS mandatory
	DESCRIPTION
		"First_source_1_branch_93_output_switch_status"
	::= { FirstGeneral_Precision_Distribution82Alarm 120 }
First_source_1_branch_94_output_switch_status OBJECT-TYPE
	SYNTAX INTEGER  {
		Normal(0),
		Alarm(1)
	}
	ACCESS read-only
	STATUS mandatory
	DESCRIPTION
		"First_source_1_branch_94_output_switch_status"
	::= { FirstGeneral_Precision_Distribution82Alarm 121 }
First_source_1_branch_95_output_switch_status OBJECT-TYPE
	SYNTAX INTEGER  {
		Normal(0),
		Alarm(1)
	}
	ACCESS read-only
	STATUS mandatory
	DESCRIPTION
		"First_source_1_branch_95_output_switch_status"
	::= { FirstGeneral_Precision_Distribution82Alarm 122 }
First_source_1_branch_96_output_switch_status OBJECT-TYPE
	SYNTAX INTEGER  {
		Normal(0),
		Alarm(1)
	}
	ACCESS read-only
	STATUS mandatory
	DESCRIPTION
		"First_source_1_branch_96_output_switch_status"
	::= { FirstGeneral_Precision_Distribution82Alarm 123 }
First_source_1_branch_97_output_switch_status OBJECT-TYPE
	SYNTAX INTEGER  {
		Normal(0),
		Alarm(1)
	}
	ACCESS read-only
	STATUS mandatory
	DESCRIPTION
		"First_source_1_branch_97_output_switch_status"
	::= { FirstGeneral_Precision_Distribution82Alarm 124 }
First_source_1_branch_98_output_switch_status OBJECT-TYPE
	SYNTAX INTEGER  {
		Normal(0),
		Alarm(1)
	}
	ACCESS read-only
	STATUS mandatory
	DESCRIPTION
		"First_source_1_branch_98_output_switch_status"
	::= { FirstGeneral_Precision_Distribution82Alarm 125 }
First_source_1_branch_99_output_switch_status OBJECT-TYPE
	SYNTAX INTEGER  {
		Normal(0),
		Alarm(1)
	}
	ACCESS read-only
	STATUS mandatory
	DESCRIPTION
		"First_source_1_branch_99_output_switch_status"
	::= { FirstGeneral_Precision_Distribution82Alarm 126 }
First_source_1_branch_100_output_switch_status OBJECT-TYPE
	SYNTAX INTEGER  {
		Normal(0),
		Alarm(1)
	}
	ACCESS read-only
	STATUS mandatory
	DESCRIPTION
		"First_source_1_branch_100_output_switch_status"
	::= { FirstGeneral_Precision_Distribution82Alarm 127 }
First_source_2_branch_1_output_switch_status OBJECT-TYPE
	SYNTAX INTEGER  {
		Normal(0),
		Alarm(1)
	}
	ACCESS read-only
	STATUS mandatory
	DESCRIPTION
		"First_source_2_branch_1_output_switch_status"
	::= { FirstGeneral_Precision_Distribution82Alarm 128 }
First_source_2_branch_2_output_switch_status OBJECT-TYPE
	SYNTAX INTEGER  {
		Normal(0),
		Alarm(1)
	}
	ACCESS read-only
	STATUS mandatory
	DESCRIPTION
		"First_source_2_branch_2_output_switch_status"
	::= { FirstGeneral_Precision_Distribution82Alarm 129 }
First_source_2_branch_3_output_switch_status OBJECT-TYPE
	SYNTAX INTEGER  {
		Normal(0),
		Alarm(1)
	}
	ACCESS read-only
	STATUS mandatory
	DESCRIPTION
		"First_source_2_branch_3_output_switch_status"
	::= { FirstGeneral_Precision_Distribution82Alarm 130 }
First_source_2_branch_4_output_switch_status OBJECT-TYPE
	SYNTAX INTEGER  {
		Normal(0),
		Alarm(1)
	}
	ACCESS read-only
	STATUS mandatory
	DESCRIPTION
		"First_source_2_branch_4_output_switch_status"
	::= { FirstGeneral_Precision_Distribution82Alarm 131 }
First_source_2_branch_5_output_switch_status OBJECT-TYPE
	SYNTAX INTEGER  {
		Normal(0),
		Alarm(1)
	}
	ACCESS read-only
	STATUS mandatory
	DESCRIPTION
		"First_source_2_branch_5_output_switch_status"
	::= { FirstGeneral_Precision_Distribution82Alarm 132 }
First_source_2_branch_6_output_switch_status OBJECT-TYPE
	SYNTAX INTEGER  {
		Normal(0),
		Alarm(1)
	}
	ACCESS read-only
	STATUS mandatory
	DESCRIPTION
		"First_source_2_branch_6_output_switch_status"
	::= { FirstGeneral_Precision_Distribution82Alarm 133 }
First_source_2_branch_7_output_switch_status OBJECT-TYPE
	SYNTAX INTEGER  {
		Normal(0),
		Alarm(1)
	}
	ACCESS read-only
	STATUS mandatory
	DESCRIPTION
		"First_source_2_branch_7_output_switch_status"
	::= { FirstGeneral_Precision_Distribution82Alarm 134 }
First_source_2_branch_8_output_switch_status OBJECT-TYPE
	SYNTAX INTEGER  {
		Normal(0),
		Alarm(1)
	}
	ACCESS read-only
	STATUS mandatory
	DESCRIPTION
		"First_source_2_branch_8_output_switch_status"
	::= { FirstGeneral_Precision_Distribution82Alarm 135 }
First_source_2_branch_9_output_switch_status OBJECT-TYPE
	SYNTAX INTEGER  {
		Normal(0),
		Alarm(1)
	}
	ACCESS read-only
	STATUS mandatory
	DESCRIPTION
		"First_source_2_branch_9_output_switch_status"
	::= { FirstGeneral_Precision_Distribution82Alarm 136 }
First_source_2_branch_10_output_switch_status OBJECT-TYPE
	SYNTAX INTEGER  {
		Normal(0),
		Alarm(1)
	}
	ACCESS read-only
	STATUS mandatory
	DESCRIPTION
		"First_source_2_branch_10_output_switch_status"
	::= { FirstGeneral_Precision_Distribution82Alarm 137 }
First_source_2_branch_11_output_switch_status OBJECT-TYPE
	SYNTAX INTEGER  {
		Normal(0),
		Alarm(1)
	}
	ACCESS read-only
	STATUS mandatory
	DESCRIPTION
		"First_source_2_branch_11_output_switch_status"
	::= { FirstGeneral_Precision_Distribution82Alarm 138 }
First_source_2_branch_12_output_switch_status OBJECT-TYPE
	SYNTAX INTEGER  {
		Normal(0),
		Alarm(1)
	}
	ACCESS read-only
	STATUS mandatory
	DESCRIPTION
		"First_source_2_branch_12_output_switch_status"
	::= { FirstGeneral_Precision_Distribution82Alarm 139 }
First_source_2_branch_13_output_switch_status OBJECT-TYPE
	SYNTAX INTEGER  {
		Normal(0),
		Alarm(1)
	}
	ACCESS read-only
	STATUS mandatory
	DESCRIPTION
		"First_source_2_branch_13_output_switch_status"
	::= { FirstGeneral_Precision_Distribution82Alarm 140 }
First_source_2_branch_14_output_switch_status OBJECT-TYPE
	SYNTAX INTEGER  {
		Normal(0),
		Alarm(1)
	}
	ACCESS read-only
	STATUS mandatory
	DESCRIPTION
		"First_source_2_branch_14_output_switch_status"
	::= { FirstGeneral_Precision_Distribution82Alarm 141 }
First_source_2_branch_15_output_switch_status OBJECT-TYPE
	SYNTAX INTEGER  {
		Normal(0),
		Alarm(1)
	}
	ACCESS read-only
	STATUS mandatory
	DESCRIPTION
		"First_source_2_branch_15_output_switch_status"
	::= { FirstGeneral_Precision_Distribution82Alarm 142 }
First_source_2_branch_16_output_switch_status OBJECT-TYPE
	SYNTAX INTEGER  {
		Normal(0),
		Alarm(1)
	}
	ACCESS read-only
	STATUS mandatory
	DESCRIPTION
		"First_source_2_branch_16_output_switch_status"
	::= { FirstGeneral_Precision_Distribution82Alarm 143 }
First_source_2_branch_17_output_switch_status OBJECT-TYPE
	SYNTAX INTEGER  {
		Normal(0),
		Alarm(1)
	}
	ACCESS read-only
	STATUS mandatory
	DESCRIPTION
		"First_source_2_branch_17_output_switch_status"
	::= { FirstGeneral_Precision_Distribution82Alarm 144 }
First_source_2_branch_18_output_switch_status OBJECT-TYPE
	SYNTAX INTEGER  {
		Normal(0),
		Alarm(1)
	}
	ACCESS read-only
	STATUS mandatory
	DESCRIPTION
		"First_source_2_branch_18_output_switch_status"
	::= { FirstGeneral_Precision_Distribution82Alarm 145 }
First_source_2_branch_19_output_switch_status OBJECT-TYPE
	SYNTAX INTEGER  {
		Normal(0),
		Alarm(1)
	}
	ACCESS read-only
	STATUS mandatory
	DESCRIPTION
		"First_source_2_branch_19_output_switch_status"
	::= { FirstGeneral_Precision_Distribution82Alarm 146 }
First_source_2_branch_20_output_switch_status OBJECT-TYPE
	SYNTAX INTEGER  {
		Normal(0),
		Alarm(1)
	}
	ACCESS read-only
	STATUS mandatory
	DESCRIPTION
		"First_source_2_branch_20_output_switch_status"
	::= { FirstGeneral_Precision_Distribution82Alarm 147 }
First_source_2_branch_21_output_switch_status OBJECT-TYPE
	SYNTAX INTEGER  {
		Normal(0),
		Alarm(1)
	}
	ACCESS read-only
	STATUS mandatory
	DESCRIPTION
		"First_source_2_branch_21_output_switch_status"
	::= { FirstGeneral_Precision_Distribution82Alarm 148 }
First_source_2_branch_22_output_switch_status OBJECT-TYPE
	SYNTAX INTEGER  {
		Normal(0),
		Alarm(1)
	}
	ACCESS read-only
	STATUS mandatory
	DESCRIPTION
		"First_source_2_branch_22_output_switch_status"
	::= { FirstGeneral_Precision_Distribution82Alarm 149 }
First_source_2_branch_23_output_switch_status OBJECT-TYPE
	SYNTAX INTEGER  {
		Normal(0),
		Alarm(1)
	}
	ACCESS read-only
	STATUS mandatory
	DESCRIPTION
		"First_source_2_branch_23_output_switch_status"
	::= { FirstGeneral_Precision_Distribution82Alarm 150 }
First_source_2_branch_24_output_switch_status OBJECT-TYPE
	SYNTAX INTEGER  {
		Normal(0),
		Alarm(1)
	}
	ACCESS read-only
	STATUS mandatory
	DESCRIPTION
		"First_source_2_branch_24_output_switch_status"
	::= { FirstGeneral_Precision_Distribution82Alarm 151 }
First_source_2_branch_25_output_switch_status OBJECT-TYPE
	SYNTAX INTEGER  {
		Normal(0),
		Alarm(1)
	}
	ACCESS read-only
	STATUS mandatory
	DESCRIPTION
		"First_source_2_branch_25_output_switch_status"
	::= { FirstGeneral_Precision_Distribution82Alarm 152 }
First_source_2_branch_26_output_switch_status OBJECT-TYPE
	SYNTAX INTEGER  {
		Normal(0),
		Alarm(1)
	}
	ACCESS read-only
	STATUS mandatory
	DESCRIPTION
		"First_source_2_branch_26_output_switch_status"
	::= { FirstGeneral_Precision_Distribution82Alarm 153 }
First_source_2_branch_27_output_switch_status OBJECT-TYPE
	SYNTAX INTEGER  {
		Normal(0),
		Alarm(1)
	}
	ACCESS read-only
	STATUS mandatory
	DESCRIPTION
		"First_source_2_branch_27_output_switch_status"
	::= { FirstGeneral_Precision_Distribution82Alarm 154 }
First_source_2_branch_28_output_switch_status OBJECT-TYPE
	SYNTAX INTEGER  {
		Normal(0),
		Alarm(1)
	}
	ACCESS read-only
	STATUS mandatory
	DESCRIPTION
		"First_source_2_branch_28_output_switch_status"
	::= { FirstGeneral_Precision_Distribution82Alarm 155 }
First_source_2_branch_29_output_switch_status OBJECT-TYPE
	SYNTAX INTEGER  {
		Normal(0),
		Alarm(1)
	}
	ACCESS read-only
	STATUS mandatory
	DESCRIPTION
		"First_source_2_branch_29_output_switch_status"
	::= { FirstGeneral_Precision_Distribution82Alarm 156 }
First_source_2_branch_30_output_switch_status OBJECT-TYPE
	SYNTAX INTEGER  {
		Normal(0),
		Alarm(1)
	}
	ACCESS read-only
	STATUS mandatory
	DESCRIPTION
		"First_source_2_branch_30_output_switch_status"
	::= { FirstGeneral_Precision_Distribution82Alarm 157 }
First_source_2_branch_31_output_switch_status OBJECT-TYPE
	SYNTAX INTEGER  {
		Normal(0),
		Alarm(1)
	}
	ACCESS read-only
	STATUS mandatory
	DESCRIPTION
		"First_source_2_branch_31_output_switch_status"
	::= { FirstGeneral_Precision_Distribution82Alarm 158 }
First_source_2_branch_32_output_switch_status OBJECT-TYPE
	SYNTAX INTEGER  {
		Normal(0),
		Alarm(1)
	}
	ACCESS read-only
	STATUS mandatory
	DESCRIPTION
		"First_source_2_branch_32_output_switch_status"
	::= { FirstGeneral_Precision_Distribution82Alarm 159 }
First_source_2_branch_33_output_switch_status OBJECT-TYPE
	SYNTAX INTEGER  {
		Normal(0),
		Alarm(1)
	}
	ACCESS read-only
	STATUS mandatory
	DESCRIPTION
		"First_source_2_branch_33_output_switch_status"
	::= { FirstGeneral_Precision_Distribution82Alarm 160 }
First_source_2_branch_34_output_switch_status OBJECT-TYPE
	SYNTAX INTEGER  {
		Normal(0),
		Alarm(1)
	}
	ACCESS read-only
	STATUS mandatory
	DESCRIPTION
		"First_source_2_branch_34_output_switch_status"
	::= { FirstGeneral_Precision_Distribution82Alarm 161 }
First_source_2_branch_35_output_switch_status OBJECT-TYPE
	SYNTAX INTEGER  {
		Normal(0),
		Alarm(1)
	}
	ACCESS read-only
	STATUS mandatory
	DESCRIPTION
		"First_source_2_branch_35_output_switch_status"
	::= { FirstGeneral_Precision_Distribution82Alarm 162 }
First_source_2_branch_36_output_switch_status OBJECT-TYPE
	SYNTAX INTEGER  {
		Normal(0),
		Alarm(1)
	}
	ACCESS read-only
	STATUS mandatory
	DESCRIPTION
		"First_source_2_branch_36_output_switch_status"
	::= { FirstGeneral_Precision_Distribution82Alarm 163 }
First_source_2_branch_37_output_switch_status OBJECT-TYPE
	SYNTAX INTEGER  {
		Normal(0),
		Alarm(1)
	}
	ACCESS read-only
	STATUS mandatory
	DESCRIPTION
		"First_source_2_branch_37_output_switch_status"
	::= { FirstGeneral_Precision_Distribution82Alarm 164 }
First_source_2_branch_38_output_switch_status OBJECT-TYPE
	SYNTAX INTEGER  {
		Normal(0),
		Alarm(1)
	}
	ACCESS read-only
	STATUS mandatory
	DESCRIPTION
		"First_source_2_branch_38_output_switch_status"
	::= { FirstGeneral_Precision_Distribution82Alarm 165 }
First_source_2_branch_39_output_switch_status OBJECT-TYPE
	SYNTAX INTEGER  {
		Normal(0),
		Alarm(1)
	}
	ACCESS read-only
	STATUS mandatory
	DESCRIPTION
		"First_source_2_branch_39_output_switch_status"
	::= { FirstGeneral_Precision_Distribution82Alarm 166 }
First_source_2_branch_40_output_switch_status OBJECT-TYPE
	SYNTAX INTEGER  {
		Normal(0),
		Alarm(1)
	}
	ACCESS read-only
	STATUS mandatory
	DESCRIPTION
		"First_source_2_branch_40_output_switch_status"
	::= { FirstGeneral_Precision_Distribution82Alarm 167 }
First_source_2_branch_41_output_switch_status OBJECT-TYPE
	SYNTAX INTEGER  {
		Normal(0),
		Alarm(1)
	}
	ACCESS read-only
	STATUS mandatory
	DESCRIPTION
		"First_source_2_branch_41_output_switch_status"
	::= { FirstGeneral_Precision_Distribution82Alarm 168 }
First_source_2_branch_42_output_switch_status OBJECT-TYPE
	SYNTAX INTEGER  {
		Normal(0),
		Alarm(1)
	}
	ACCESS read-only
	STATUS mandatory
	DESCRIPTION
		"First_source_2_branch_42_output_switch_status"
	::= { FirstGeneral_Precision_Distribution82Alarm 169 }
First_source_2_branch_43_output_switch_status OBJECT-TYPE
	SYNTAX INTEGER  {
		Normal(0),
		Alarm(1)
	}
	ACCESS read-only
	STATUS mandatory
	DESCRIPTION
		"First_source_2_branch_43_output_switch_status"
	::= { FirstGeneral_Precision_Distribution82Alarm 170 }
First_source_2_branch_44_output_switch_status OBJECT-TYPE
	SYNTAX INTEGER  {
		Normal(0),
		Alarm(1)
	}
	ACCESS read-only
	STATUS mandatory
	DESCRIPTION
		"First_source_2_branch_44_output_switch_status"
	::= { FirstGeneral_Precision_Distribution82Alarm 171 }
First_source_2_branch_45_output_switch_status OBJECT-TYPE
	SYNTAX INTEGER  {
		Normal(0),
		Alarm(1)
	}
	ACCESS read-only
	STATUS mandatory
	DESCRIPTION
		"First_source_2_branch_45_output_switch_status"
	::= { FirstGeneral_Precision_Distribution82Alarm 172 }
First_source_2_branch_46_output_switch_status OBJECT-TYPE
	SYNTAX INTEGER  {
		Normal(0),
		Alarm(1)
	}
	ACCESS read-only
	STATUS mandatory
	DESCRIPTION
		"First_source_2_branch_46_output_switch_status"
	::= { FirstGeneral_Precision_Distribution82Alarm 173 }
First_source_2_branch_47_output_switch_status OBJECT-TYPE
	SYNTAX INTEGER  {
		Normal(0),
		Alarm(1)
	}
	ACCESS read-only
	STATUS mandatory
	DESCRIPTION
		"First_source_2_branch_47_output_switch_status"
	::= { FirstGeneral_Precision_Distribution82Alarm 174 }
First_source_2_branch_48_output_switch_status OBJECT-TYPE
	SYNTAX INTEGER  {
		Normal(0),
		Alarm(1)
	}
	ACCESS read-only
	STATUS mandatory
	DESCRIPTION
		"First_source_2_branch_48_output_switch_status"
	::= { FirstGeneral_Precision_Distribution82Alarm 175 }
First_source_2_branch_49_output_switch_status OBJECT-TYPE
	SYNTAX INTEGER  {
		Normal(0),
		Alarm(1)
	}
	ACCESS read-only
	STATUS mandatory
	DESCRIPTION
		"First_source_2_branch_49_output_switch_status"
	::= { FirstGeneral_Precision_Distribution82Alarm 176 }
First_source_2_branch_50_output_switch_status OBJECT-TYPE
	SYNTAX INTEGER  {
		Normal(0),
		Alarm(1)
	}
	ACCESS read-only
	STATUS mandatory
	DESCRIPTION
		"First_source_2_branch_50_output_switch_status"
	::= { FirstGeneral_Precision_Distribution82Alarm 177 }
First_source_2_branch_51_output_switch_status OBJECT-TYPE
	SYNTAX INTEGER  {
		Normal(0),
		Alarm(1)
	}
	ACCESS read-only
	STATUS mandatory
	DESCRIPTION
		"First_source_2_branch_51_output_switch_status"
	::= { FirstGeneral_Precision_Distribution82Alarm 178 }
First_source_2_branch_52_output_switch_status OBJECT-TYPE
	SYNTAX INTEGER  {
		Normal(0),
		Alarm(1)
	}
	ACCESS read-only
	STATUS mandatory
	DESCRIPTION
		"First_source_2_branch_52_output_switch_status"
	::= { FirstGeneral_Precision_Distribution82Alarm 179 }
First_source_2_branch_53_output_switch_status OBJECT-TYPE
	SYNTAX INTEGER  {
		Normal(0),
		Alarm(1)
	}
	ACCESS read-only
	STATUS mandatory
	DESCRIPTION
		"First_source_2_branch_53_output_switch_status"
	::= { FirstGeneral_Precision_Distribution82Alarm 180 }
First_source_2_branch_54_output_switch_status OBJECT-TYPE
	SYNTAX INTEGER  {
		Normal(0),
		Alarm(1)
	}
	ACCESS read-only
	STATUS mandatory
	DESCRIPTION
		"First_source_2_branch_54_output_switch_status"
	::= { FirstGeneral_Precision_Distribution82Alarm 181 }
First_source_2_branch_55_output_switch_status OBJECT-TYPE
	SYNTAX INTEGER  {
		Normal(0),
		Alarm(1)
	}
	ACCESS read-only
	STATUS mandatory
	DESCRIPTION
		"First_source_2_branch_55_output_switch_status"
	::= { FirstGeneral_Precision_Distribution82Alarm 182 }
First_source_2_branch_56_output_switch_status OBJECT-TYPE
	SYNTAX INTEGER  {
		Normal(0),
		Alarm(1)
	}
	ACCESS read-only
	STATUS mandatory
	DESCRIPTION
		"First_source_2_branch_56_output_switch_status"
	::= { FirstGeneral_Precision_Distribution82Alarm 183 }
First_source_2_branch_57_output_switch_status OBJECT-TYPE
	SYNTAX INTEGER  {
		Normal(0),
		Alarm(1)
	}
	ACCESS read-only
	STATUS mandatory
	DESCRIPTION
		"First_source_2_branch_57_output_switch_status"
	::= { FirstGeneral_Precision_Distribution82Alarm 184 }
First_source_2_branch_58_output_switch_status OBJECT-TYPE
	SYNTAX INTEGER  {
		Normal(0),
		Alarm(1)
	}
	ACCESS read-only
	STATUS mandatory
	DESCRIPTION
		"First_source_2_branch_58_output_switch_status"
	::= { FirstGeneral_Precision_Distribution82Alarm 185 }
First_source_2_branch_59_output_switch_status OBJECT-TYPE
	SYNTAX INTEGER  {
		Normal(0),
		Alarm(1)
	}
	ACCESS read-only
	STATUS mandatory
	DESCRIPTION
		"First_source_2_branch_59_output_switch_status"
	::= { FirstGeneral_Precision_Distribution82Alarm 186 }
First_source_2_branch_60_output_switch_status OBJECT-TYPE
	SYNTAX INTEGER  {
		Normal(0),
		Alarm(1)
	}
	ACCESS read-only
	STATUS mandatory
	DESCRIPTION
		"First_source_2_branch_60_output_switch_status"
	::= { FirstGeneral_Precision_Distribution82Alarm 187 }
First_source_2_branch_61_output_switch_status OBJECT-TYPE
	SYNTAX INTEGER  {
		Normal(0),
		Alarm(1)
	}
	ACCESS read-only
	STATUS mandatory
	DESCRIPTION
		"First_source_2_branch_61_output_switch_status"
	::= { FirstGeneral_Precision_Distribution82Alarm 188 }
First_source_2_branch_62_output_switch_status OBJECT-TYPE
	SYNTAX INTEGER  {
		Normal(0),
		Alarm(1)
	}
	ACCESS read-only
	STATUS mandatory
	DESCRIPTION
		"First_source_2_branch_62_output_switch_status"
	::= { FirstGeneral_Precision_Distribution82Alarm 189 }
First_source_2_branch_63_output_switch_status OBJECT-TYPE
	SYNTAX INTEGER  {
		Normal(0),
		Alarm(1)
	}
	ACCESS read-only
	STATUS mandatory
	DESCRIPTION
		"First_source_2_branch_63_output_switch_status"
	::= { FirstGeneral_Precision_Distribution82Alarm 190 }
First_source_2_branch_64_output_switch_status OBJECT-TYPE
	SYNTAX INTEGER  {
		Normal(0),
		Alarm(1)
	}
	ACCESS read-only
	STATUS mandatory
	DESCRIPTION
		"First_source_2_branch_64_output_switch_status"
	::= { FirstGeneral_Precision_Distribution82Alarm 191 }
First_source_2_branch_65_output_switch_status OBJECT-TYPE
	SYNTAX INTEGER  {
		Normal(0),
		Alarm(1)
	}
	ACCESS read-only
	STATUS mandatory
	DESCRIPTION
		"First_source_2_branch_65_output_switch_status"
	::= { FirstGeneral_Precision_Distribution82Alarm 192 }
First_source_2_branch_66_output_switch_status OBJECT-TYPE
	SYNTAX INTEGER  {
		Normal(0),
		Alarm(1)
	}
	ACCESS read-only
	STATUS mandatory
	DESCRIPTION
		"First_source_2_branch_66_output_switch_status"
	::= { FirstGeneral_Precision_Distribution82Alarm 193 }
First_source_2_branch_67_output_switch_status OBJECT-TYPE
	SYNTAX INTEGER  {
		Normal(0),
		Alarm(1)
	}
	ACCESS read-only
	STATUS mandatory
	DESCRIPTION
		"First_source_2_branch_67_output_switch_status"
	::= { FirstGeneral_Precision_Distribution82Alarm 194 }
First_source_2_branch_68_output_switch_status OBJECT-TYPE
	SYNTAX INTEGER  {
		Normal(0),
		Alarm(1)
	}
	ACCESS read-only
	STATUS mandatory
	DESCRIPTION
		"First_source_2_branch_68_output_switch_status"
	::= { FirstGeneral_Precision_Distribution82Alarm 195 }
First_source_2_branch_69_output_switch_status OBJECT-TYPE
	SYNTAX INTEGER  {
		Normal(0),
		Alarm(1)
	}
	ACCESS read-only
	STATUS mandatory
	DESCRIPTION
		"First_source_2_branch_69_output_switch_status"
	::= { FirstGeneral_Precision_Distribution82Alarm 196 }
First_source_2_branch_70_output_switch_status OBJECT-TYPE
	SYNTAX INTEGER  {
		Normal(0),
		Alarm(1)
	}
	ACCESS read-only
	STATUS mandatory
	DESCRIPTION
		"First_source_2_branch_70_output_switch_status"
	::= { FirstGeneral_Precision_Distribution82Alarm 197 }
First_source_2_branch_71_output_switch_status OBJECT-TYPE
	SYNTAX INTEGER  {
		Normal(0),
		Alarm(1)
	}
	ACCESS read-only
	STATUS mandatory
	DESCRIPTION
		"First_source_2_branch_71_output_switch_status"
	::= { FirstGeneral_Precision_Distribution82Alarm 198 }
First_source_2_branch_72_output_switch_status OBJECT-TYPE
	SYNTAX INTEGER  {
		Normal(0),
		Alarm(1)
	}
	ACCESS read-only
	STATUS mandatory
	DESCRIPTION
		"First_source_2_branch_72_output_switch_status"
	::= { FirstGeneral_Precision_Distribution82Alarm 199 }
First_source_2_branch_73_output_switch_status OBJECT-TYPE
	SYNTAX INTEGER  {
		Normal(0),
		Alarm(1)
	}
	ACCESS read-only
	STATUS mandatory
	DESCRIPTION
		"First_source_2_branch_73_output_switch_status"
	::= { FirstGeneral_Precision_Distribution82Alarm 200 }
First_source_2_branch_74_output_switch_status OBJECT-TYPE
	SYNTAX INTEGER  {
		Normal(0),
		Alarm(1)
	}
	ACCESS read-only
	STATUS mandatory
	DESCRIPTION
		"First_source_2_branch_74_output_switch_status"
	::= { FirstGeneral_Precision_Distribution82Alarm 201 }
First_source_2_branch_75_output_switch_status OBJECT-TYPE
	SYNTAX INTEGER  {
		Normal(0),
		Alarm(1)
	}
	ACCESS read-only
	STATUS mandatory
	DESCRIPTION
		"First_source_2_branch_75_output_switch_status"
	::= { FirstGeneral_Precision_Distribution82Alarm 202 }
First_source_2_branch_76_output_switch_status OBJECT-TYPE
	SYNTAX INTEGER  {
		Normal(0),
		Alarm(1)
	}
	ACCESS read-only
	STATUS mandatory
	DESCRIPTION
		"First_source_2_branch_76_output_switch_status"
	::= { FirstGeneral_Precision_Distribution82Alarm 203 }
First_source_2_branch_77_output_switch_status OBJECT-TYPE
	SYNTAX INTEGER  {
		Normal(0),
		Alarm(1)
	}
	ACCESS read-only
	STATUS mandatory
	DESCRIPTION
		"First_source_2_branch_77_output_switch_status"
	::= { FirstGeneral_Precision_Distribution82Alarm 204 }
First_source_2_branch_78_output_switch_status OBJECT-TYPE
	SYNTAX INTEGER  {
		Normal(0),
		Alarm(1)
	}
	ACCESS read-only
	STATUS mandatory
	DESCRIPTION
		"First_source_2_branch_78_output_switch_status"
	::= { FirstGeneral_Precision_Distribution82Alarm 205 }
First_source_2_branch_79_output_switch_status OBJECT-TYPE
	SYNTAX INTEGER  {
		Normal(0),
		Alarm(1)
	}
	ACCESS read-only
	STATUS mandatory
	DESCRIPTION
		"First_source_2_branch_79_output_switch_status"
	::= { FirstGeneral_Precision_Distribution82Alarm 206 }
First_source_2_branch_80_output_switch_status OBJECT-TYPE
	SYNTAX INTEGER  {
		Normal(0),
		Alarm(1)
	}
	ACCESS read-only
	STATUS mandatory
	DESCRIPTION
		"First_source_2_branch_80_output_switch_status"
	::= { FirstGeneral_Precision_Distribution82Alarm 207 }
First_source_2_branch_81_output_switch_status OBJECT-TYPE
	SYNTAX INTEGER  {
		Normal(0),
		Alarm(1)
	}
	ACCESS read-only
	STATUS mandatory
	DESCRIPTION
		"First_source_2_branch_81_output_switch_status"
	::= { FirstGeneral_Precision_Distribution82Alarm 208 }
First_source_2_branch_82_output_switch_status OBJECT-TYPE
	SYNTAX INTEGER  {
		Normal(0),
		Alarm(1)
	}
	ACCESS read-only
	STATUS mandatory
	DESCRIPTION
		"First_source_2_branch_82_output_switch_status"
	::= { FirstGeneral_Precision_Distribution82Alarm 209 }
First_source_2_branch_83_output_switch_status OBJECT-TYPE
	SYNTAX INTEGER  {
		Normal(0),
		Alarm(1)
	}
	ACCESS read-only
	STATUS mandatory
	DESCRIPTION
		"First_source_2_branch_83_output_switch_status"
	::= { FirstGeneral_Precision_Distribution82Alarm 210 }
First_source_2_branch_84_output_switch_status OBJECT-TYPE
	SYNTAX INTEGER  {
		Normal(0),
		Alarm(1)
	}
	ACCESS read-only
	STATUS mandatory
	DESCRIPTION
		"First_source_2_branch_84_output_switch_status"
	::= { FirstGeneral_Precision_Distribution82Alarm 211 }
First_source_2_branch_85_output_switch_status OBJECT-TYPE
	SYNTAX INTEGER  {
		Normal(0),
		Alarm(1)
	}
	ACCESS read-only
	STATUS mandatory
	DESCRIPTION
		"First_source_2_branch_85_output_switch_status"
	::= { FirstGeneral_Precision_Distribution82Alarm 212 }
First_source_2_branch_86_output_switch_status OBJECT-TYPE
	SYNTAX INTEGER  {
		Normal(0),
		Alarm(1)
	}
	ACCESS read-only
	STATUS mandatory
	DESCRIPTION
		"First_source_2_branch_86_output_switch_status"
	::= { FirstGeneral_Precision_Distribution82Alarm 213 }
First_source_2_branch_87_output_switch_status OBJECT-TYPE
	SYNTAX INTEGER  {
		Normal(0),
		Alarm(1)
	}
	ACCESS read-only
	STATUS mandatory
	DESCRIPTION
		"First_source_2_branch_87_output_switch_status"
	::= { FirstGeneral_Precision_Distribution82Alarm 214 }
First_source_2_branch_88_output_switch_status OBJECT-TYPE
	SYNTAX INTEGER  {
		Normal(0),
		Alarm(1)
	}
	ACCESS read-only
	STATUS mandatory
	DESCRIPTION
		"First_source_2_branch_88_output_switch_status"
	::= { FirstGeneral_Precision_Distribution82Alarm 215 }
First_source_2_branch_89_output_switch_status OBJECT-TYPE
	SYNTAX INTEGER  {
		Normal(0),
		Alarm(1)
	}
	ACCESS read-only
	STATUS mandatory
	DESCRIPTION
		"First_source_2_branch_89_output_switch_status"
	::= { FirstGeneral_Precision_Distribution82Alarm 216 }
First_source_2_branch_90_output_switch_status OBJECT-TYPE
	SYNTAX INTEGER  {
		Normal(0),
		Alarm(1)
	}
	ACCESS read-only
	STATUS mandatory
	DESCRIPTION
		"First_source_2_branch_90_output_switch_status"
	::= { FirstGeneral_Precision_Distribution82Alarm 217 }
First_source_2_branch_91_output_switch_status OBJECT-TYPE
	SYNTAX INTEGER  {
		Normal(0),
		Alarm(1)
	}
	ACCESS read-only
	STATUS mandatory
	DESCRIPTION
		"First_source_2_branch_91_output_switch_status"
	::= { FirstGeneral_Precision_Distribution82Alarm 218 }
First_source_2_branch_92_output_switch_status OBJECT-TYPE
	SYNTAX INTEGER  {
		Normal(0),
		Alarm(1)
	}
	ACCESS read-only
	STATUS mandatory
	DESCRIPTION
		"First_source_2_branch_92_output_switch_status"
	::= { FirstGeneral_Precision_Distribution82Alarm 219 }
First_source_2_branch_93_output_switch_status OBJECT-TYPE
	SYNTAX INTEGER  {
		Normal(0),
		Alarm(1)
	}
	ACCESS read-only
	STATUS mandatory
	DESCRIPTION
		"First_source_2_branch_93_output_switch_status"
	::= { FirstGeneral_Precision_Distribution82Alarm 220 }
First_source_2_branch_94_output_switch_status OBJECT-TYPE
	SYNTAX INTEGER  {
		Normal(0),
		Alarm(1)
	}
	ACCESS read-only
	STATUS mandatory
	DESCRIPTION
		"First_source_2_branch_94_output_switch_status"
	::= { FirstGeneral_Precision_Distribution82Alarm 221 }
First_source_2_branch_95_output_switch_status OBJECT-TYPE
	SYNTAX INTEGER  {
		Normal(0),
		Alarm(1)
	}
	ACCESS read-only
	STATUS mandatory
	DESCRIPTION
		"First_source_2_branch_95_output_switch_status"
	::= { FirstGeneral_Precision_Distribution82Alarm 222 }
First_source_2_branch_96_output_switch_status OBJECT-TYPE
	SYNTAX INTEGER  {
		Normal(0),
		Alarm(1)
	}
	ACCESS read-only
	STATUS mandatory
	DESCRIPTION
		"First_source_2_branch_96_output_switch_status"
	::= { FirstGeneral_Precision_Distribution82Alarm 223 }
First_source_2_branch_97_output_switch_status OBJECT-TYPE
	SYNTAX INTEGER  {
		Normal(0),
		Alarm(1)
	}
	ACCESS read-only
	STATUS mandatory
	DESCRIPTION
		"First_source_2_branch_97_output_switch_status"
	::= { FirstGeneral_Precision_Distribution82Alarm 224 }
First_source_2_branch_98_output_switch_status OBJECT-TYPE
	SYNTAX INTEGER  {
		Normal(0),
		Alarm(1)
	}
	ACCESS read-only
	STATUS mandatory
	DESCRIPTION
		"First_source_2_branch_98_output_switch_status"
	::= { FirstGeneral_Precision_Distribution82Alarm 225 }
First_source_2_branch_99_output_switch_status OBJECT-TYPE
	SYNTAX INTEGER  {
		Normal(0),
		Alarm(1)
	}
	ACCESS read-only
	STATUS mandatory
	DESCRIPTION
		"First_source_2_branch_99_output_switch_status"
	::= { FirstGeneral_Precision_Distribution82Alarm 226 }
First_source_2_branch_100_output_switch_status OBJECT-TYPE
	SYNTAX INTEGER  {
		Normal(0),
		Alarm(1)
	}
	ACCESS read-only
	STATUS mandatory
	DESCRIPTION
		"First_source_2_branch_100_output_switch_status"
	::= { FirstGeneral_Precision_Distribution82Alarm 227 }


-- Traps
--General_Precision_Distribution82Trap
--addGeneral_Precision_Distribution82Trap
General_Precision_Distribution82AlarmAdd NOTIFICATION-TYPE 
  STATUS      current 
	DESCRIPTION 
 "SEVERE: Alarm occur!" 

	::= { General_Precision_Distribution82AlarmTrap 100 }
General_Precision_Distribution82AlarmRemove NOTIFICATION-TYPE 
  STATUS      current 
	DESCRIPTION 
 "SEVERE: Alarm cancel!" 

	::= { General_Precision_Distribution82AlarmTrap 101 }


END
