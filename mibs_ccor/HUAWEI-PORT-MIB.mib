-- ===================================================================
-- Copyright (C) 2018 by HUAWEI TECHNOLOGIES. All rights reserved.
-- Description:
-- Reference:
-- Version: V2.86
-- ===================================================================
HUAWEI-PORT-MIB DEFINITIONS ::= BEGIN
    IMPORTS
        EnabledStatus
            FROM P-BRIDGE-MIB
        InterfaceIndex
            FROM IF-MIB
        ImaFrameLength, ImaGroupState
            FROM HUAWEI-IMA-MIB
        MODULE-IDENTITY, OBJECT-TYPE, NOTIFICATION-TYPE, Integer32, Unsigned32, Counter64, IpAddress
            FROM SNMPv2-SMI
        TruthValue, RowStatus, TEXTUAL-CONVENTION
            FROM SNMPv2-TC
        hwDatacomm
            FROM HUAWEI-MIB
        NOTIFICATION-GROUP, OBJECT-GROUP, MODULE-COMPLIANCE
            FROM SNMPv2-CONF     
        DateAndTime            
                FROM SNMPv2-TC
        entPhysicalName            
                FROM ENTITY-MIB
        hwGtlItemIndex, hwGtlItemName
            FROM HUAWEI-GTL-MIB;

    hwPortMIB MODULE-IDENTITY
        LAST-UPDATED "201801111100Z"
        ORGANIZATION "Huawei Technologies Co.,Ltd."
        CONTACT-INFO
            "Huawei Industrial Base
                  Bantian, Longgang
                   Shenzhen 518129
                   People's Republic of China
                   Website: http://www.huawei.com
                   Email: support@huawei.com"
        DESCRIPTION 
            "The private mib file includes the general extent
            information of the device.hwDatacomm(157).hwPortMIB" 

        -- Add revision info here!
        REVISION "201801111100Z"
        DESCRIPTION
        "modify hwPhysicalPortPortType,hwPhysicalPortAlarmReason"

        -- Add revision info here!
        REVISION "201801051029Z"
        DESCRIPTION
        "modify hwEthernetJumboframeMaxLength"

        -- Add revision info here!
        REVISION "201711231027Z"
        DESCRIPTION
        "add hwEthoamClosePortAlarmResume"

        -- Add revision info here!
        REVISION "201711091549Z"
        DESCRIPTION
        "add hwPortTypeChangeTrap, hwComboSwitchFail, hwComboSwitchFailResume"

        -- Add revision info here!
        REVISION "201711031538Z"
        DESCRIPTION
        "add hwEthoamClosePortAlarm"

        -- Add revision info here!
        REVISION "201710231549Z"
        DESCRIPTION
        "add hwPvcNumAlarm, hwPvcNumAlarmResume"

        -- Add revision info here!
        REVISION "201709250950Z"
        DESCRIPTION
        "add hwVxlanTrunkHashNotSupport"

        -- Add revision info here!
        REVISION "201709232136Z"
        DESCRIPTION
        "add hwFlexEPhyDelayOverAlarm,hwFlexEPhyDelayOverAlarmResume,hwFlexESubTimeSlotMismatch,hwFlexESubTimeSlotMismatchResume"   

            -- Add revision info here!
        REVISION "201709141537Z"
        DESCRIPTION
        "modify hwFxsoPortMode "

        -- Add revision info here!
        REVISION "201709091813Z"
        DESCRIPTION
        "add hwOtnFecMode OBJECT-TYPE SYNTAX INTEGER lhaulsd(5)"

        -- Add revision info here!
        REVISION "201709042136Z"
        DESCRIPTION
        "add hwFlexEPhyNumberMismatch,hwFlexEPhyNumberMismatchResume,hwFlexEPhyGroupMismatch,hwFlexEPhyGroupMismatchResume,
            hwFlexEClientIDMismatch,hwFlexEClientIDMismatchResume,hwFlexEBwReduceAlarm,hwFlexEBwReduceAlarmResume,hwFlexEPhyFcsSdAlarm,
            hwFlexEPhyFcsSdAlarmResume,hwFlexEPhyLocalFaultAlarm,hwFlexEPhyLocalFaultAlarmResume,hwFlexEPhyRemoteFaultAlarm,
            hwFlexEPhyRemoteFaultAlarmResume,hwFlexEBwMismatch,hwFlexEBwMismatchResume"            
            
        -- Add revision info here!
        REVISION "201707081826Z"
        DESCRIPTION
        "add hwCableSnrAbnormal,hwCableSnrNormal,hwCableSnrDetectNotSupport"
        
        -- Add revision info here!
        REVISION "201704272334Z"
        DESCRIPTION
        "modify hwEthernetSpeedSet."

        REVISION "201703281130Z"
        DESCRIPTION
        "add hwPortLicenseActFail,hwPortLicenseActSuccess."
      -- Add revision info here!
		REVISION "201703150909Z"
        DESCRIPTION
        "add blockAc alarm."
        -- Add revision info here!
		REVISION "201701241430Z"
        DESCRIPTION
        "add hwNbAcBlock hwNbRealTimeDelay."

		-- Add revision info here!
		REVISION "201701041730Z"
        DESCRIPTION
        "add hwPortProtectGroupId,hwPortProtectGroupAvailable,hwPortProtectGroupDelete."
		
		-- Add revision info here!
		REVISION "201612161730Z"
        DESCRIPTION
        "add hwBoardNotSupportAssignTrunk."
		
		-- Add revision info here!
        REVISION "201610122026Z"
        DESCRIPTION
        "modify hwEthernetJumboframeMaxLength."

	REVISION "201609252334Z"
        DESCRIPTION
        "modify hwEthernetSpeedSet."
	
	REVISION "201608151106Z"
        DESCRIPTION
        "Add hwPhysicalPortInBroadcastRapidChange, hwInputBroadcastChangeThreshold, hwCurrentStatisticalInputBroadcast, hwBaseStatisticalInputBroadcast."
		
        REVISION "201608022211Z"
        DESCRIPTION
        "modify hwImpedanceMismatch."


        REVISION "201607251508Z"
        DESCRIPTION
        "Add hwPicLcdAlarm ,hwPicLcdAlarmResume."
		
		
        REVISION "201607211145Z"
        DESCRIPTION
        "Add hwImpedenceMismatch."


		 REVISION "201606161054Z"
        DESCRIPTION 
		"Add hwPhysicalPortName of this mib nodes:hwPtimAlarm,hwB3TcaAlarm,hwPplmAlarm,hwPrdiAlarm,hwLomAlarm,hwPuneqAlarm,hwPaisAlarm."
		-- Add revision info here!
        REVISION "201605111850Z"
        DESCRIPTION
        "Add hwPortGroupTransModeDiff,hwPortGroupTransModeDiffResume,hwPhysicalPortGroupID,hwPortTransModeReasonDescr."
		
        -- Add revision info here!
        REVISION "201605041850Z"
        DESCRIPTION
        "Add hwPortErrorRateExceed."

        REVISION "201604251526Z"
        DESCRIPTION
         "Add hwIPIfStatTable."
            
        REVISION "201604180926Z"
        DESCRIPTION
        "Add hwPortSpeedChangeTrap,hwPhysicalPortCurSpeed,hwPhysicalPortLastSpeed."
        
		REVISION "201603291516Z"		-- March 29, 2016 at 15:16 GMT
		DESCRIPTION 
		"Add hwSubIfNumExceededSpecTrapObject,hwSubIfSpecNum,hwSubIfNumExceededSpecAlarm,hwSubIfNumExceededSpecAlarmResume."				

        REVISION "201602171634Z"
        DESCRIPTION
        "Add hwPortCrcRateExceed."
         
        REVISION "201512011108Z"
        DESCRIPTION
        "Add hwNbPortType."

        REVISION "201510191105Z"
        DESCRIPTION
        "Modify hwCollisionAlarm,hwCollisionAlarmResume."

        REVISION "201510161105Z"
        DESCRIPTION
        "Modify hwRdiAlarm,hwRdiAlarmResume,hwAisAlarm ,hwAisAlarmResume,hwCollisionAlarm,hwCollisionAlarmResume."
		
        REVISION "201510091105Z"
        DESCRIPTION
        "Add hwRdiAlarm,hwRdiAlarmResume,hwAisAlarm ,hwAisAlarmResume,hwCollisionAlarm,hwCollisionAlarmResume."

        REVISION "201508221138Z"
        DESCRIPTION
        "Add hwPortModeChange,hwPhysicalPortMode."

        REVISION "201508221138Z"
        DESCRIPTION
        "Increased the default Mib node for hwEthernetFlowControl."

        REVISION "201508221138Z"
        DESCRIPTION
        "Add hwLicenseInactiveAlarm,hwLicenseInactiveAlarmResume,hwLicenseResourceLackAlarm,hwLicenseResourceLackAlarmResume."
		
        REVISION "201507101139Z"
        DESCRIPTION
        "Add hwPortTotalStatistics."

        REVISION "201504110000Z"
        DESCRIPTION
        "Add hwPortPhysicalRate, hwPortPhysicalRateDegradeAlarm, hwPortPhysicalRateDegradeAlarmResume."
	
        -- Add revision info here!
	REVISION "201504100000Z"
        DESCRIPTION
        "Add hwPhysicalPortName of this mib nodes: hwAuAisAlarm, hwB3ExcAlarm, hwBip2ExcAlarm, hwBip2TcaAlarm,
         hwCposE1AlmE1RaiAlarm, hwCposE1DownE1AisAlarm, hwCposE1LfaAlarm, hwCposE1LmfaAlarm, hwCposE1UpE1AisAlarm,
	 hwLpSlmVc12Alarm, hwLpTimVc12Alarm, hwLpUneqVc12Alarm, hwTuAisVc12Alarm, hwV5VcaisAlarm, hwVlopAlarm, hwVrdiAlarm, hwVrfiAlarm"
	
        -- Add revision info here!  
        REVISION "201504030000Z"
        DESCRIPTION
        "Add hwInputRateChangeThresholdPercent, hwOutputRateChangeThresholdPercent, hwCurrentStatisticalPeriodRate, hwLastStatisticalPeriodRate, hwInputRateChangeOverThresholdNotice, hwOutputRateChangeOverThresholdNotice."
	
        REVISION "201503250000Z"
        DESCRIPTION
        "Add hwLinkHeartbeat trap"

        REVISION "201503241002Z"
        DESCRIPTION
            "Modify description of symbol error alarm high and low threshold."

      -- Add revision info here!  
        REVISION "201503191000Z"
        DESCRIPTION
        "Add hwNbCommonTable and its leafs, add x50 lof,abit alarms"

        -- Add revision info here!
        REVISION "201503161416Z"
        DESCRIPTION
            "Modify description of crc error alarm high and low threshold."

          REVISION "201503021009Z"
        DESCRIPTION
        "Modified hwEthernetSpeedSet."

        REVISION "201502060000Z"
        DESCRIPTION
        "Increased the otn Mib leafs for the WDM interface."

        -- Add revision info here!  
        REVISION "201501311400Z"
        DESCRIPTION
        "Add hwNarrowBand and its tables and leafs."

        REVISION "201408221142Z"
        DESCRIPTION
        "Modify the description of the  hwEthHalfDuplex and hwEthFullDuplex."

        REVISION "201408221142Z"
        DESCRIPTION
        "Bind hwPhysicalPortAlarmName to hwDslLinkSignalLost and hwDslLinkSignalResume ."

        REVISION "201408221142Z"
        DESCRIPTION
        "Add hwMultiServiceOnOneCardAlarm,hwMultiServiceOnOneCardAlarmResume."
 
        REVISION "201408221142Z"
        DESCRIPTION
            "Add hwLogicalPort."

        REVISION "201406121140Z"
        DESCRIPTION
            "Add hwPhysicalPortFlowSurge, hwInputBroadcastSurgeOccur, hwInputBroadcastSurgeResume, hwOutputBroadcastSurgeOccur, hwOutputBroadcastSurgeResume."

        REVISION "201404162141Z"
        DESCRIPTION
            "Increased the otn Mib nodes for the WDM interface."

        REVISION "201404111150Z"
        DESCRIPTION
            "Increased two OBJECT-TYPE nodes hwPhysicalPortPreFecCoefficientStatistics and hwPhysicalPortPreFecPowerStatistics.
             Increased two traps hwPrefecTcaAlarm and hwPrefecTcaAlarmResume."
           
		   
        REVISION "201404021011Z"
        DESCRIPTION
             "Added a object named hwPRBSTestInfo and it includes 4 tables : hwPRBSTestPortStatusTable,hwPRBSTestResultTable,
	     hwPRBSTestIntervalTable and hwPRBSTestSegmentTable.hwPRBSTestPortStatusTable includes 10 nodes : 
	     hwPRBSTestPortStatusIfName,hwPRBSTestPortStatusSide,hwPRBSTestPortStatusSuportFlag,hwPRBSTestPortStatusPatternBitmap,
             hwPRBSTestPortStatusErrInsertLevel,hwPRBSTestPortStatusSlotNum,hwPRBSTestPortStatusCardNum,
             hwPRBSTestPortStatusPhyPortIfName,hwPRBSTestPortStatusResultCount,hwPRBSTestPortStatusOngoingTestIndex.
	     hwPRBSTestResultTable includes 25 nodes : hwPRBSTestResultIfName,hwPRBSTestResultTestIndex,
             hwPRBSTestResultPhyPortIfName,hwPRBSTestResultSide,hwPRBSTestResultPattern,hwPRBSTestResultIntervalTime,
             hwPRBSTestResultIntervalCount,hwPRBSTestResultTestingIntervalIndex,hwPRBSTestResultStartTime,
             hwPRBSTestResultStopTime,hwPRBSTestResultProgress,hwPRBSTestResultRemainTime,hwPRBSTestResultErrInserted,
             hwPRBSTestResultTotalBit,hwPRBSTestResultErrorBit,hwPRBSTestResultBerCoe,hwPRBSTestResultBerPow,
             hwPRBSTestResultLos,hwPRBSTestResultEs,hwPRBSTestResultEfs,hwPRBSTestResultSes,hwPRBSTestResultUas,
             hwPRBSTestResultSegmentTime,hwPRBSTestResultSegmentTotalCount,hwPRBSTestResultTestingSegmentIndex.
	     hwPRBSTestIntervalTable includes 17 nodes : hwPRBSTestIntervalIfName,hwPRBSTestIntervalTestIndex,
             hwPRBSTestIntervalIndex,hwPRBSTestIntervalStartTime,hwPRBSTestIntervalStopTime,hwPRBSTestIntervalProgress,
             hwPRBSTestIntervalRemainTime,hwPRBSTestIntervalErrInserted,hwPRBSTestIntervalTotalBit,hwPRBSTestIntervalErrorBit,
             hwPRBSTestIntervalBerCoe,hwPRBSTestIntervalBerPow,hwPRBSTestIntervalLos,hwPRBSTestIntervalEs,
             hwPRBSTestIntervalEfs,hwPRBSTestIntervalSes,hwPRBSTestIntervalUas.hwPRBSTestSegmentTable includes 14 nodes : 
	     hwPRBSTestSegmentIfName,hwPRBSTestSegmentTestIndex,hwPRBSTestSegmentIndex,hwPRBSTestSegmentStartTime,
             hwPRBSTestSegmentEndTime,hwPRBSTestSegmentTotalBit,hwPRBSTestSegmentErrorBit,hwPRBSTestSegmentBerCoe,
             hwPRBSTestSegmentBerPow,hwPRBSTestSegmentLos,hwPRBSTestSegmentEs,hwPRBSTestSegmentEfs,hwPRBSTestSegmentSes,
             hwPRBSTestSegmentUas."
	     
   
             
        REVISION "201403311711Z"
        DESCRIPTION
             "Modified hwPhysicalLoopbackType."        

        REVISION "201403241700Z"
        DESCRIPTION
             "Add hwPhysicalPortCrcPerWarningThresholdCoefficient, hwPhysicalPortCrcPerWarningThresholdPower, 
              hwPhysicalPortCrcPerWarningResumeThresholdCoefficient, hwPhysicalPortCrcPerWarningResumeThresholdPower,
              hwPhysicalPortCrcPerWarningThresholdString, hwPhysicalPortCrcPerWarningResumeThresholdString;
              Add hwPhysicalPortCrcPerWarning and hwPhysicalPortCrcPerWarningResume"

        REVISION "201402211038Z"
        DESCRIPTION
             "Modified hwEthernetSpeedSet."
        
        REVISION "201402141135Z"
        DESCRIPTION
             "Increased 4 traps hwE3UpE3AisAlarm and hwE3UpE3AisAlarmResume and hwE3AlmE3RaiAlarm and hwE3AlmE3RaiAlarmResume."
       
        REVISION "201312240955Z"
        DESCRIPTION
             "Increased 24 traps hwOtuLomAlarm and hwOtuLomAlarmResume and hwOtuAisAlarm and hwOtuAisAlarmResume and 
                hwOtuSdAlarm and hwOtuSdAlarmResume and hwOtuSfAlarm and hwOtuSfAlarmResume and hwSmBdiAlarm and 
                hwSmBdiAlarmResume and hwSmIaeAlarm and hwSmIaeAlarmResume and hwSmTimAlarm and hwSmTimAlarmResume and 
                hwOduAisAlarm and hwOduAisAlarmResume and hwOduLokAlarm and hwOduLokAlarmResume and hwOduOciAlarm and 
                hwOduOciAlarmResume and hwPmBdiAlarm and hwPmBdiAlarmResume and hwPmTimAlarm and hwPmTimAlarmResume."

        REVISION "201312231101Z"
        DESCRIPTION
             "Modified hwDs0ChannelBundleSpeed."

        REVISION "201312041642Z"
        DESCRIPTION
             "Increased two nodes hwPhysicalPortCrcSdAlarmTriggerLsp and hwPhysicalPortCrcExcAlarmTriggerLsp."

        REVISION "201311161154Z"
        DESCRIPTION
            "Increased two nodes hwPhysicalPortCrcPerAlarmCoefficientStatistics and hwPhysicalPortCrcPerAlarmPowerStatistics."
            
        REVISION "201310281016Z"
        DESCRIPTION
            "Add hwNotSameBoardInTrunk"

        REVISION "201310142026Z"
        DESCRIPTION
            "Add hwPortDescription."

        REVISION "201309060954Z"
        DESCRIPTION
            "Add four nodes hwPhysicalPortCrcSd and hwPhysicalPortCrcSdResume 
              and hwPhysicalPortCrcExc and hwPhysicalPortCrcExcResume."
        
        REVISION "201308082127Z"
        DESCRIPTION
            "Add hwPhysicalPortAutoDetectFail and hwPhysicalPortAutoDetectSuccess."

        REVISION "201307091716Z"
        DESCRIPTION
            "Add hwPortLine and hwPortIfStatistics."

        REVISION "201307051425Z"
        DESCRIPTION
            "Add one nodes  hwCposVc4Flag and one STRING object hwPhysicalPortAlarmName ."

        REVISION "201306271422Z"
        DESCRIPTION
            "Add hwPortProtectGroupCfg."
            
        REVISION "201306141851Z"
        DESCRIPTION
            "Add half-duplex alarm."    

        REVISION "201305311751Z"
        DESCRIPTION
            "Add negotiation failed alarm."

        REVISION "201305081751Z"
        DESCRIPTION
            "THE PRIVATE MIB FILE INCLUDES THE GENERAL EXTENT
                INFORMATION OF THE DEVICE.HWDATACOMM(157).HWPORTMIB"

        REVISION "201303251039Z"
        DESCRIPTION
            "Increased two nodes hwCopperPolarityError and hwCopperPolarityErrorResume."

        REVISION "201105180930Z"
        DESCRIPTION
            "Initial version."

        ::= { hwDatacomm 157 }

    hwPortMIBObjects OBJECT IDENTIFIER ::= { hwPortMIB 1 }

    hwEthernet OBJECT IDENTIFIER ::= { hwPortMIBObjects 1 }

    hwEthernetTable OBJECT-TYPE
        SYNTAX  SEQUENCE OF HwEthernetEntry
        MAX-ACCESS not-accessible
        STATUS current
        DESCRIPTION
            "This table describes the access and configuration of physical attributes of various Ethernet interfaces."
        ::= { hwEthernet 1 }


    hwEthernetEntry OBJECT-TYPE
        SYNTAX HwEthernetEntry 
        MAX-ACCESS not-accessible
        STATUS current
        DESCRIPTION
            "Indicates the physical attributes of the Ethernet interface.
                This table lists the physical attributes of various Ethernet interfaces."
        INDEX { hwEthernetIfIndex }
        ::= { hwEthernetTable 1 }


    HwEthernetEntry ::= SEQUENCE {
        hwEthernetIfIndex 
            InterfaceIndex,
        hwEthernetLoopback 
            INTEGER,
        hwEthernetPortType 
            INTEGER,
        hwEthernetSpeedSet 
            INTEGER,
        hwEthernetDuplex 
            INTEGER,
        hwEthernetNegotiation 
            EnabledStatus,
        hwEthernetPortTypeOperate 
            INTEGER,
        hwEthernetClock 
            INTEGER,
        hwEthernetFlagJ0Mode 
            INTEGER,
        hwEthernetFlagJ0Value 
            Integer32,
        hwEthernetFlagJ0Trace 
            OCTET STRING,
        hwEthernetFlagJ1Mode 
            INTEGER,
        hwEthernetFlagJ1Value 
            Integer32,
        hwEthernetFlagJ1Trace 
            OCTET STRING,
        hwEthernetFlagC2Value 
            Integer32,
        hwEthernetUpHoldTime 
            Integer32,
        hwEthernetDownHoldTime 
            Integer32,
        hwEthernetSubinterfaceStatisticEnable 
            EnabledStatus,
        hwEthernetFlowControl 
            INTEGER,
        hwEthernetOffline 
            INTEGER,
        hwEthernetSetTransferMode 
            INTEGER,
        hwEthernetJumboframeMaxLength 
            Integer32,
        hwEthernetComboType 
            INTEGER,
        hwEthernetPortMode 
            INTEGER,
        hwEthernetNegotiationMode 
            INTEGER
        }


    hwEthernetIfIndex OBJECT-TYPE
        SYNTAX InterfaceIndex 
        MAX-ACCESS not-accessible
        STATUS current
        DESCRIPTION
            "This object indicates the interface index."
        ::= { hwEthernetEntry 1 }


    hwEthernetLoopback OBJECT-TYPE
        SYNTAX INTEGER {otherLoop(1),stopLoopback(2),local(3),remote(4)}
        MAX-ACCESS read-write
        STATUS current
        DESCRIPTION
            "This object indicates the internal loop (local loopback) function, which is used to test a local interface. When the interface works normally, the local loopback function must be disabled. By default, stopLoopback is set."
        ::= { hwEthernetEntry 11 }


    hwEthernetPortType OBJECT-TYPE
        SYNTAX INTEGER {other(1),copper(2),fiber(3)}
        MAX-ACCESS read-write
        STATUS current
        DESCRIPTION
            "This object indicates the type of an Ethernet interface, either the optical interface or the electrical interface."
        ::= { hwEthernetEntry 12 }


    hwEthernetSpeedSet OBJECT-TYPE
        SYNTAX INTEGER {other(1),speed10(2),speed100(3),speed1000(4),speed10000(5),speed40000(6),speed20000(7),speed2500(8),speed5000(9),speed100000(10),speed12000(11),speed48000(12)}
        MAX-ACCESS read-write
        STATUS current
        DESCRIPTION
            "This object indicates the transmission rate of the Ethernet interface. You can configure transmission rates for only certain Ethernet electrical interfaces, and you cannot configure transmission rates for optical interfaces. The transmission rate for an electrical interface can be set to 10M, 100M, or 1000M."
        ::= { hwEthernetEntry 13 }


    hwEthernetDuplex OBJECT-TYPE
        SYNTAX INTEGER {full(1),half(2)}
        MAX-ACCESS read-write
        STATUS current
        DESCRIPTION
            "This object indicates the duplex mode of an Ethernet interface. Ethernet electrical interfaces can work in either half-duplex or full-duplex mode. Ethernet optical interfaces can work only in full-duplex mode."
        ::= { hwEthernetEntry 14 }


    hwEthernetNegotiation OBJECT-TYPE
        SYNTAX EnabledStatus 
        MAX-ACCESS read-write
        STATUS current
        DESCRIPTION
            "This object indicates whether auto-negotiation is enabled on an Ethernet electrical interface. 
			 The default value is enable. For an Ethernet electrical interface, hwEthernetSpeedSet, hwEthernetDuplex, and hwEthernetNegotiation are associated with each other. 
			 If hwEthernetNegotiation is set to enable, the values of hwEthernetSpeedSet and hwEthernetDuplex are obtained through auto-negotiation.
			 When hwEthernetSpeedSet is forcibly set to a value, hwEthernetDuplex is then automatically changed to full (the default value), and hwEthernetNegotiation is automatically changed to disable. 
			 If hwEthernetNegotiation is set to enable, you cannot set a value for hwEthernetDuplex. For an Ethernet optical interface, you can set a value for hwEthernetNegotiation, and hwEthernetNegotiation is not associated with hwEthernetSpeedSet or hwEthernetDuplex."
        ::= { hwEthernetEntry 15 }


    hwEthernetPortTypeOperate OBJECT-TYPE
        SYNTAX INTEGER {other(1),copper(2),fiber100(3),fiber1000(4)}
        MAX-ACCESS read-write
        STATUS current
        DESCRIPTION
            "This object indicates the link type of an Ethernet interface, either optical fibers or cables. This object is only supported by certain Ethernet interfaces."
        ::= { hwEthernetEntry 16 }


    hwEthernetClock OBJECT-TYPE
        SYNTAX INTEGER {master(1),slave(2)}
        MAX-ACCESS read-write
        STATUS current
        DESCRIPTION
            "This object indicates the clock mode. By default, the slave clock mode is used. Only WAN interfaces require the clock configuration."
        ::= { hwEthernetEntry 20 }


    hwEthernetFlagJ0Mode OBJECT-TYPE
        SYNTAX INTEGER {j01ByteMode(1),j016ByteMode(2),j064ByteOrNullMode(3),peer(4)}
        MAX-ACCESS read-write
        STATUS current
        DESCRIPTION
            "This object indicates that 10GE WAN interfaces have to use SDH/SONET as the frame format and the overhead byte has to be set. The overhead byte of an SDH frame can be: j0: indicates the section trace byte. The default value is j016ByteMode(2).
             hwEthernetFlagJ0Trace: NetEngine."
        ::= { hwEthernetEntry 21 }


    hwEthernetFlagJ0Value OBJECT-TYPE
        SYNTAX Integer32 (0..255)
        MAX-ACCESS read-write
        STATUS current
        DESCRIPTION
            "This object indicates that when hwEthernetFlagJ0Mode is set to j01ByteMode, this object takes effect."
        ::= { hwEthernetEntry 22 }


    hwEthernetFlagJ0Trace OBJECT-TYPE
        SYNTAX OCTET STRING (SIZE (0..64))
        MAX-ACCESS read-write
        STATUS current
        DESCRIPTION
            "This object indicates the section trace byte. When hwEthernetFlagJ0Mode is set to j016ByteMode or j064ByteOrNullMode, this object takes effect.
			 When hwEthernetFlagJ0Mode is set to j016ByteMode, the value of hwEthernetFlagJ0Trace is up to 15 characters; when hwEthernetFlagJ0Mode is set to j064ByteOrNullMode, the value of hwEthernetFlagJ0Trace is up to 64 characters."
        ::= { hwEthernetEntry 23 }


    hwEthernetFlagJ1Mode OBJECT-TYPE
        SYNTAX INTEGER {j11ByteMode(1),j116ByteMode(2),j164ByteOrNullMode(3),peer(4)}
        MAX-ACCESS read-write
        STATUS current
        DESCRIPTION
            "This object indicates the overhead byte of an SDH frame. j1 indicates the path trace byte. By default, the value is j116ByteMode(2): hwEthernetFlagJ1Trace: NetEngine."
        ::= { hwEthernetEntry 24 }


    hwEthernetFlagJ1Value OBJECT-TYPE
        SYNTAX Integer32 (0..255)
        MAX-ACCESS read-write
        STATUS current
        DESCRIPTION
            "This object indicates that when hwEthernetFlagJ1Mode is set to j11ByteMode, this object takes effect."
        ::= { hwEthernetEntry 25 }


    hwEthernetFlagJ1Trace OBJECT-TYPE
        SYNTAX OCTET STRING (SIZE (0..64))
        MAX-ACCESS read-write
        STATUS current
        DESCRIPTION
            "This object indicates the path trace byte. When hwEthernetFlagJ1Mode is set to j116ByteMode or j164ByteOrNullMode, this object takes effect. When hwEthernetFlagJ1Mode is set to j116ByteMode, the value of this object is up to 15 characters. When hwEthernetFlagJ1Mode is set to j164ByteOrNullMode, the value of this object is up to 64 characters."
        ::= { hwEthernetEntry 26 }


    hwEthernetFlagC2Value OBJECT-TYPE
        SYNTAX Integer32 (0..255)
        MAX-ACCESS read-write
        STATUS current
        DESCRIPTION
            "This object indicates the overhead byte of the SDH frame.
			 C2: indicates the path signal label byte. The value ranges from 00 to FF, in the hexadecimal format. The default value is 26 (0x1a)."
        ::= { hwEthernetEntry 27 }


    hwEthernetUpHoldTime OBJECT-TYPE
        SYNTAX Integer32 (0..86400000)
        MAX-ACCESS read-write
        STATUS current
        DESCRIPTION
            "This object indicates the time period during which the interface remains Up."
        ::= { hwEthernetEntry 31 }


    hwEthernetDownHoldTime OBJECT-TYPE
        SYNTAX Integer32 (0..86400000)
        MAX-ACCESS read-write
        STATUS current
        DESCRIPTION
            "This object indicates the time period during which the interface remains Down."
        ::= { hwEthernetEntry 32 }


    hwEthernetSubinterfaceStatisticEnable OBJECT-TYPE
        SYNTAX EnabledStatus 
        MAX-ACCESS read-write
        STATUS current
        DESCRIPTION
            "This object indicates statistics collection is enabled for a sub-interface."
        ::= { hwEthernetEntry 33 }


    hwEthernetFlowControl OBJECT-TYPE
        SYNTAX INTEGER {receive(1),send(2),both(3),none(4),default(5)}
        MAX-ACCESS read-write
        STATUS current
        DESCRIPTION
            "This object indicates the interface flow control status."
        ::= { hwEthernetEntry 34 }


    hwEthernetOffline OBJECT-TYPE
        SYNTAX INTEGER {true(1),false(2)}
        MAX-ACCESS read-write
        STATUS current
        DESCRIPTION
            "This object indicates that the physical protocol status of an interface is Down."
        ::= { hwEthernetEntry 35 }


    hwEthernetSetTransferMode OBJECT-TYPE
        SYNTAX INTEGER {lan(1),wan(2),none(3),otn(4)}
        MAX-ACCESS read-write
        STATUS current
        DESCRIPTION
            "This object indicates the LAN-WAN mode of an Ethernet interface."
        ::= { hwEthernetEntry 36 }


    hwEthernetJumboframeMaxLength OBJECT-TYPE
        SYNTAX Integer32 (1520..16000)
        MAX-ACCESS read-write
        STATUS current
        DESCRIPTION
            "This object indicates the maximum length of the Jumbo frame on an interface."
        ::= { hwEthernetEntry 37 }


    hwEthernetComboType OBJECT-TYPE
        SYNTAX INTEGER {auto(1),copper(2),fiber(3),other(4)}
        MAX-ACCESS read-write
        STATUS current
        DESCRIPTION
            "combo mode of this port."
        ::= { hwEthernetEntry 38 }


    hwEthernetPortMode OBJECT-TYPE
        SYNTAX INTEGER {copper(1),fiber(2),other(3)}
        MAX-ACCESS read-only
        STATUS current
        DESCRIPTION
            "Indicates combo mode of this port."
        ::= { hwEthernetEntry 39 }


    hwEthernetNegotiationMode OBJECT-TYPE
        SYNTAX INTEGER {notsupport(1),auto(2),master(3),slave(4)}
        MAX-ACCESS read-write
        STATUS current
        DESCRIPTION
            "Set negotiation-mode for phy of electronic GE port.The mode is uesed for synchronizing clock. "
        ::= { hwEthernetEntry 40 }


    hwPos OBJECT IDENTIFIER ::= { hwPortMIBObjects 2 }

    hwPosTable OBJECT-TYPE
        SYNTAX  SEQUENCE OF HwPosEntry
        MAX-ACCESS not-accessible
        STATUS current
        DESCRIPTION
            "This table describes the access and configuration of physical attributes of various POS interfaces."
        ::= { hwPos 1 }


    hwPosEntry OBJECT-TYPE
        SYNTAX HwPosEntry 
        MAX-ACCESS not-accessible
        STATUS current
        DESCRIPTION
            "Indicates the physical attributes of the POS interface.
                This table lists the physical attributes of the POS interface."
        INDEX { hwPosIfIndex }
        ::= { hwPosTable 1 }


    HwPosEntry ::= SEQUENCE {
        hwPosIfIndex 
            InterfaceIndex,
        hwPosLinkProtocol 
            INTEGER,
        hwPosFrameFormat 
            INTEGER,
        hwPosLoopback 
            INTEGER,
        hwPosScramble 
            EnabledStatus,
        hwPosClock 
            INTEGER,
        hwPosCrcVerifyCode 
            INTEGER,
        hwPosFlagJ0Mode 
            INTEGER,
        hwPosFlagJ0Value 
            Integer32,
        hwPosFlagJ0Trace 
            OCTET STRING,
        hwPosFlagJ1Mode 
            INTEGER,
        hwPosFlagJ1Value 
            Integer32,
        hwPosFlagJ1Trace 
            OCTET STRING,
        hwPosFlagC2Value 
            Integer32
        }


    hwPosIfIndex OBJECT-TYPE
        SYNTAX InterfaceIndex 
        MAX-ACCESS not-accessible
        STATUS current
        DESCRIPTION
            "Interface index(es) of port(s) present on the device ."
        ::= { hwPosEntry 1 }


    hwPosLinkProtocol OBJECT-TYPE
        SYNTAX INTEGER {ietf(1),nonstandard(2),hdlc(3),ppp(4)}
        MAX-ACCESS read-write
        STATUS current
        DESCRIPTION
            "This object indicates the link layer protocol running on a POS interface. By default, a POS interface uses PPP as the link layer protocol."
        ::= { hwPosEntry 11 }


    hwPosFrameFormat OBJECT-TYPE
        SYNTAX INTEGER {sonet(1),sdh(2)}
        MAX-ACCESS read-write
        STATUS current
        DESCRIPTION
            "This object indicates the frame type on a POS interface. By default, the frame type is SDH."
        ::= { hwPosEntry 12 }


    hwPosLoopback OBJECT-TYPE
        SYNTAX INTEGER {otherLoop(1),stopLoopback(2),local(3),remote(4)}
        MAX-ACCESS read-write
        STATUS current
        DESCRIPTION
            "This object indicates the internal loop (local loopback) function on a POS interface, which is used to test a local interface. 
			 When the interface works normally, the local loopback function must be disabled. By default, stopLoopback is set."
        ::= { hwPosEntry 13 }


    hwPosScramble OBJECT-TYPE
        SYNTAX EnabledStatus 
        MAX-ACCESS read-write
        STATUS current
        DESCRIPTION
            "This object indicates whether the payload scramble function is enabled on a POS interface. By default, the scramble function is enabled."
        ::= { hwPosEntry 14 }


    hwPosClock OBJECT-TYPE
        SYNTAX INTEGER {master(1),slave(2)}
        MAX-ACCESS read-write
        STATUS current
        DESCRIPTION
            "This object indicates the clock mode. By default, the slave clock mode is used."
        ::= { hwPosEntry 15 }


    hwPosCrcVerifyCode OBJECT-TYPE
        SYNTAX INTEGER {crc16(1),crc32(2)}
        MAX-ACCESS read-write
        STATUS current
        DESCRIPTION
            "This object indicates the length of the CRC field. By default, the length is 32."
        ::= { hwPosEntry 16 }


    hwPosFlagJ0Mode OBJECT-TYPE
        SYNTAX INTEGER {j01ByteMode(1),j016ByteMode(2),j064ByteOrNullMode(3),peer(4)}
        MAX-ACCESS read-write
        STATUS current
        DESCRIPTION
            "This object indicates the overhead byte of an SDH frame. The value can be:
			 j0: indicates the section trace byte. The default value is j016ByteMode(2).
			 hwEthernetFlagJ0Trace: NetEngine."
        ::= { hwPosEntry 21 }


    hwPosFlagJ0Value OBJECT-TYPE
        SYNTAX Integer32 (0..127)
        MAX-ACCESS read-write
        STATUS current
        DESCRIPTION
            "This object indicates that when hwPosFlagJ0Mode is set to j01ByteMode, this object takes effect."
        ::= { hwPosEntry 22 }


    hwPosFlagJ0Trace OBJECT-TYPE
        SYNTAX OCTET STRING (SIZE (0..64))
        MAX-ACCESS read-write
        STATUS current
        DESCRIPTION
            "This object indicates the section trace byte. When hwPosFlagJ0Mode is set to j016ByteMode or j064ByteOrNullMode, this object takes effect. 
			 When hwPosFlagJ0Mode is set to j016ByteMode, the value of hwPosFlagJ0Mode is up to 15 characters; when hwPosFlagJ0Mode is set to j064ByteOrNullMode, the value of hwPosFlagJ0Mode is up to 64 characters."
        ::= { hwPosEntry 23 }


    hwPosFlagJ1Mode OBJECT-TYPE
        SYNTAX INTEGER {j11ByteMode(1),j116ByteMode(2),j164ByteOrNullMode(3),peer(4)}
        MAX-ACCESS read-write
        STATUS current
        DESCRIPTION
            "This object indicates the overhead byte of an SDH frame. j1 indicates the path trace byte. The default value is j116ByteMode(2). hwPosFlagJ1Trace: NetEngine."
        ::= { hwPosEntry 24 }


    hwPosFlagJ1Value OBJECT-TYPE
        SYNTAX Integer32 (0..127)
        MAX-ACCESS read-write
        STATUS current
        DESCRIPTION
            "This object indicates the j1-1byte-mode value. When hwPosFlagJ1Mode is set to j11ByteMode, this object takes effect."
        ::= { hwPosEntry 25 }


    hwPosFlagJ1Trace OBJECT-TYPE
        SYNTAX OCTET STRING (SIZE (0..64))
        MAX-ACCESS read-write
        STATUS current
        DESCRIPTION
            "This object indicates the path trace byte. When hwPosFlagJ1Mode is set to j116ByteMode or j164ByteOrNullMode, this object takes effect. 
			 When hwPosFlagJ1Mode is set to j116ByteMode, the value of hwPosFlagJ1Mode is up to 15 characters; when hwPosFlagJ1Mode is set to j164ByteOrNullMode, the value of hwPosFlagJ1Mode is up to 64 characters."
        ::= { hwPosEntry 26 }


    hwPosFlagC2Value OBJECT-TYPE
        SYNTAX Integer32 (0..255)
        MAX-ACCESS read-write
        STATUS current
        DESCRIPTION
            "This object indicates the overhead byte of an SDH frame. C2 indicates the path signal label byte. The value ranges from 00 to FF in the hexadecimal format. The default value is 22 (0x16)."
        ::= { hwPosEntry 27 }


    hwCpos OBJECT IDENTIFIER ::= { hwPortMIBObjects 3 }

    hwCposTable OBJECT-TYPE
        SYNTAX  SEQUENCE OF HwCposEntry
        MAX-ACCESS not-accessible
        STATUS current
        DESCRIPTION
            "Indicates the physical attributes of the CPOS interface.
                This table lists the physical attributes of the CPOS interface."
        ::= { hwCpos 1 }


    hwCposEntry OBJECT-TYPE
        SYNTAX HwCposEntry 
        MAX-ACCESS not-accessible
        STATUS current
        DESCRIPTION
            "Indicates the physical attributes of the CPOS interface.
                This table lists the physical attributes of the CPOS interface."
        INDEX { hwCposIfIndex }
        ::= { hwCposTable 1 }


    HwCposEntry ::= SEQUENCE {
        hwCposIfIndex 
            InterfaceIndex,
        hwCposClock 
            INTEGER,
        hwCposIfType 
            INTEGER,
        hwCposFrameFormat 
            INTEGER,
        hwCposMultiplex 
            INTEGER,
        hwCposLoopback 
            INTEGER,
        hwCposFlagJ0Mode 
            INTEGER,
        hwCposFlagJ0Value 
            Integer32,
        hwCposFlagJ0Trace 
            OCTET STRING,
        hwCposFlagJ1Mode 
            INTEGER,
        hwCposFlagJ1Value 
            Integer32,
        hwCposFlagJ1Trace 
            OCTET STRING,
        hwCposFlagC2Value 
            Integer32,
        hwCposB1SdAlarmThreshold 
            Integer32,
        hwCposB1ExcAlarmThreshold 
            Integer32,
        hwCposB2SdAlarmThreshold 
            Integer32,
        hwCposB2ExcAlarmThreshold 
            Integer32,
        hwCposB3SdAlarmThreshold 
            Integer32,
        hwCposB3ExcAlarmThreshold 
            Integer32,
        hwCposLpBipSdAlarmThreshold 
            Integer32,
        hwCposLpBipExcAlarmThreshold 
            Integer32,
        hwCposHighPathNumber 
            Integer32,
        hwCposLowPathNumber 
            Integer32,
        hwCposMappingMode 
            INTEGER,
        hwCposRxJ0Mode 
            INTEGER,
        hwCposRxJ1Mode 
            INTEGER,
        hwCposRxJ0Value 
            Integer32,
        hwCposRxJ1Value 
            Integer32,
        hwCposRxJ0Trace 
            OCTET STRING,
        hwCposRxJ1Trace 
            OCTET STRING,
       hwCposVc4Flag 
            Integer32
        }


    hwCposIfIndex OBJECT-TYPE
        SYNTAX InterfaceIndex 
        MAX-ACCESS not-accessible
        STATUS current
        DESCRIPTION
            "Interface index(es) of port(s) present on the device ."
        ::= { hwCposEntry 1 }


    hwCposClock OBJECT-TYPE
        SYNTAX INTEGER {master(1),slave(2)}
        MAX-ACCESS read-write
        STATUS current
        DESCRIPTION
            "Indicates whether the clock is in master mode or slave mode.
                By default, the clock is in slave mode."
        ::= { hwCposEntry 11 }


    hwCposIfType OBJECT-TYPE
        SYNTAX INTEGER {stm1(1),stm16(2)}
        MAX-ACCESS read-write
        STATUS current
        DESCRIPTION
            "Indicates the interface type."
        ::= { hwCposEntry 12 }


    hwCposFrameFormat OBJECT-TYPE
        SYNTAX INTEGER {sonet(1),sdh(2)}
        MAX-ACCESS read-write
        STATUS current
        DESCRIPTION
            "Indicates the frame type of the CPOS interface. By default, the frame type of the CPOS interface is SDH."
        ::= { hwCposEntry 13 }


    hwCposMultiplex OBJECT-TYPE
        SYNTAX INTEGER {au3(1),au4(2)}
        MAX-ACCESS read-write
        STATUS current
        DESCRIPTION
            "Indicates the multiplex mode of the AUG. By default, the multiplex mode of the AUG is au-4."
        ::= { hwCposEntry 14 }


    hwCposLoopback OBJECT-TYPE
        SYNTAX INTEGER {otherloop(1),stopLoopback(2),local(3),remote(4)}
        MAX-ACCESS read-write
        STATUS current
        DESCRIPTION
            "Indicates the loopback function of the CPOS interface. By default, the loopback function is disabled."
        ::= { hwCposEntry 15 }


    hwCposFlagJ0Mode OBJECT-TYPE
        SYNTAX INTEGER {j01ByteMode(1),j016ByteMode(2),j064ByteOrNullMode(3),peer(4)}
        MAX-ACCESS read-write
        STATUS current
        DESCRIPTION
            "Indicates the overhead byte of the SDH frame. j0: sets section trace byte.
                The default value is j016ByteMode(2);hwCposFlagJ0Trace NetEngine."
        ::= { hwCposEntry 21 }


    hwCposFlagJ0Value OBJECT-TYPE
        SYNTAX Integer32 (0..127)
        MAX-ACCESS read-write
        STATUS current
        DESCRIPTION
            "j01ByteMode Value . When hwCposFlagJ0Mode is set to j01ByteMode, hwCposFlagJ0Value takes effect."
        ::= { hwCposEntry 22 }


    hwCposFlagJ0Trace OBJECT-TYPE
        SYNTAX OCTET STRING (SIZE (0..64))
        MAX-ACCESS read-write
        STATUS current
        DESCRIPTION
            "Set section trace byte.
                When hwCposFlagJ0Mode is set to j016ByteMode or j064ByteOrNullMode, this variable takes effect.
                When hwCposFlagJ0Mode is set to j016ByteMode, this variable is up to 15 characters trace byte.
                When hwCposFlagJ0Mode is set to j064ByteOrNullMode, this variable is up to 64 characters trace byte."
        ::= { hwCposEntry 23 }


    hwCposFlagJ1Mode OBJECT-TYPE
        SYNTAX INTEGER {j11ByteMode(1),j116ByteMode(2),j164ByteOrNullMode(3),peer(4)}
        MAX-ACCESS read-write
        STATUS current
        DESCRIPTION
            "Indicates the overhead byte of the SDH frame. j1: sets path trace byte.
                The default value is j116ByteMode(2);hwCposFlagJ1Trace NetEngine."
        ::= { hwCposEntry 24 }


    hwCposFlagJ1Value OBJECT-TYPE
        SYNTAX Integer32 (0..127)
        MAX-ACCESS read-write
        STATUS current
        DESCRIPTION
            "Indicates the value of j11ByteMode. When hwCposFlagJ1Mode is set to j11ByteMode, hwCposFlagJ1Value takes effect."
        ::= { hwCposEntry 25 }


    hwCposFlagJ1Trace OBJECT-TYPE
        SYNTAX OCTET STRING (SIZE (0..64))
        MAX-ACCESS read-write
        STATUS current
        DESCRIPTION
            "Set path trace byte.
                When hwCposFlagJ1Mode is set to j116ByteMode or j164ByteOrNullMode, this variable takes effect.
                When hwCposFlagJ1Mode is set to j116ByteMode, this variable is a string up to 15 characters trace byte.
                When hwCposFlagJ1Mode is set to j164ByteOrNullMode, this variable is a string up to 64 characters trace byte."
        ::= { hwCposEntry 26 }


    hwCposFlagC2Value OBJECT-TYPE
        SYNTAX Integer32 (0..255)
        MAX-ACCESS read-write
        STATUS current
        DESCRIPTION
            "Indicates the overhead byte of the SDH frame.
                c2: indicates the signal label byte. It is a hexdecimal value ranging from 00 to FF.
                The default value is 22(0x16)."
        ::= { hwCposEntry 27 }


    hwCposB1SdAlarmThreshold OBJECT-TYPE
        SYNTAX Integer32 (1..9)
        MAX-ACCESS read-write
        STATUS current
        DESCRIPTION
            "The threshold of B1 threshold crossing alarm."
        DEFVAL { 6 }
        ::= { hwCposEntry 28 }


    hwCposB1ExcAlarmThreshold OBJECT-TYPE
        SYNTAX Integer32 (1..9)
        MAX-ACCESS read-write
        STATUS current
        DESCRIPTION
            "The threshold of B1 threshold crossing alarm."
        DEFVAL { 3 }
        ::= { hwCposEntry 29 }


    hwCposB2SdAlarmThreshold OBJECT-TYPE
        SYNTAX Integer32 (1..9)
        MAX-ACCESS read-write
        STATUS current
        DESCRIPTION
            "The threshold of B2 threshold crossing alarm."
        DEFVAL { 6 }
        ::= { hwCposEntry 30 }


    hwCposB2ExcAlarmThreshold OBJECT-TYPE
        SYNTAX Integer32 (1..9)
        MAX-ACCESS read-write
        STATUS current
        DESCRIPTION
            "The threshold of B2 threshold crossing alarm."
        DEFVAL { 3 }
        ::= { hwCposEntry 31 }


    hwCposB3SdAlarmThreshold OBJECT-TYPE
        SYNTAX Integer32 (1..9)
        MAX-ACCESS read-write
        STATUS current
        DESCRIPTION
            "The threshold of B3 threshold crossing alarm."
        DEFVAL { 6 }
        ::= { hwCposEntry 32 }


    hwCposB3ExcAlarmThreshold OBJECT-TYPE
        SYNTAX Integer32 (1..9)
        MAX-ACCESS read-write
        STATUS current
        DESCRIPTION
            "The threshold of B3 threshold crossing alarm."
        DEFVAL { 3 }
        ::= { hwCposEntry 33 }


    hwCposLpBipSdAlarmThreshold OBJECT-TYPE
        SYNTAX Integer32 (1..9)
        MAX-ACCESS read-write
        STATUS current
        DESCRIPTION
            "The threshold of BIP2 threshold crossing alarm."
        DEFVAL { 6 }
        ::= { hwCposEntry 34 }


    hwCposLpBipExcAlarmThreshold OBJECT-TYPE
        SYNTAX Integer32 (1..9)
        MAX-ACCESS read-write
        STATUS current
        DESCRIPTION
            "The threshold of BIP2 threshold crossing alarm."
        DEFVAL { 3 }
        ::= { hwCposEntry 35 }


    hwCposHighPathNumber OBJECT-TYPE
        SYNTAX Integer32 (0..255)
        MAX-ACCESS read-only
        STATUS current
        DESCRIPTION
            "Indicates the overhead byte of the SDH frame.
                c2: indicates the signal label byte. It is a hexdecimal value ranging from 00 to FF.
                The default value is 22(0x16)."
        ::= { hwCposEntry 36 }


    hwCposLowPathNumber OBJECT-TYPE
        SYNTAX Integer32 (0..255)
        MAX-ACCESS read-only
        STATUS current
        DESCRIPTION
            "Indicates the overhead byte of the SDH frame.
                c2: indicates the signal label byte. It is a hexdecimal value ranging from 00 to FF.
                The default value is 22(0x16)."
        ::= { hwCposEntry 37 }


    hwCposMappingMode OBJECT-TYPE
        SYNTAX INTEGER {hMode(1),lMode(2),aMode(3)}
        MAX-ACCESS read-write
        STATUS current
        DESCRIPTION
            "Indicates the mapping mode of cpos port, default if h-mode(1)."
        ::= { hwCposEntry 38 }


    hwCposRxJ0Mode OBJECT-TYPE
        SYNTAX INTEGER {j01ByteMode(1),j016ByteMode(2),j064ByteOrNullMode(3),peer(4)}
        MAX-ACCESS read-only
        STATUS current
        DESCRIPTION
            "Indicates the received J0 mode."
        ::= { hwCposEntry 39 }


    hwCposRxJ1Mode OBJECT-TYPE
        SYNTAX INTEGER {j11ByteMode(1),j116ByteMode(2),j164ByteOrNullMode(3),peer(4)}
        MAX-ACCESS read-only
        STATUS current
        DESCRIPTION
            "Indicates the received J1 mode."
        ::= { hwCposEntry 40 }


    hwCposRxJ0Value OBJECT-TYPE
        SYNTAX Integer32 (0..127)
        MAX-ACCESS read-only
        STATUS current
        DESCRIPTION
            "Indicates the received J0 value of 1-byte mode."
        ::= { hwCposEntry 41 }


    hwCposRxJ1Value OBJECT-TYPE
        SYNTAX Integer32 (0..127)
        MAX-ACCESS read-only
        STATUS current
        DESCRIPTION
            "Indicates the received J1 value of 1-byte mode."
        ::= { hwCposEntry 42 }


    hwCposRxJ0Trace OBJECT-TYPE
        SYNTAX OCTET STRING (SIZE (0..64))
        MAX-ACCESS read-only
        STATUS current
        DESCRIPTION
            "Indicates the received J0 characters of 16-byte or 64-byte mode."
        ::= { hwCposEntry 43 }


    hwCposRxJ1Trace OBJECT-TYPE
        SYNTAX OCTET STRING (SIZE (0..64))
        MAX-ACCESS read-only
        STATUS current
        DESCRIPTION
            "Indicates the received J1 characters of 16-byte or 64-byte mode."
        ::= { hwCposEntry 44 }


    hwCposVc4Flag OBJECT-TYPE
        SYNTAX Integer32 (0..2)
        MAX-ACCESS read-only
        STATUS current
        DESCRIPTION
            "The value of this object identifies whether a VC4 channel can be created on the CPOS interface. 
             0 indicates that no VC4 channel can be created on the CPOS interface.
             1 indicates that a VC4 channel can be created but has not been created on the CPOS interface. 
             2 indicates that a VC4 channel can be created and has been created on the CPOS interface."
        ::= { hwCposEntry 45 }



    hwPortPhysicalHpIndex OBJECT-TYPE
        SYNTAX Integer32 
        MAX-ACCESS accessible-for-notify
        STATUS current
        DESCRIPTION
            "Indicates the higher order path number."
        ::= { hwCpos 2 }


    hwPortPhysicalLpIndex OBJECT-TYPE
        SYNTAX Integer32 
        MAX-ACCESS accessible-for-notify
        STATUS current
        DESCRIPTION
            "Indicates the low order path number."
        ::= { hwCpos 3 }


    hwCposLpTable OBJECT-TYPE
        SYNTAX  SEQUENCE OF HwCposLpEntry
        MAX-ACCESS not-accessible
        STATUS current
        DESCRIPTION
            "Description."
        ::= { hwCpos 4 }


    hwCposLpEntry OBJECT-TYPE
        SYNTAX HwCposLpEntry 
        MAX-ACCESS not-accessible
        STATUS current
        DESCRIPTION
            "Description."
        INDEX { hwCposLpIfIndex,hwCposLpId }
        ::= { hwCposLpTable 1 }


    HwCposLpEntry ::= SEQUENCE {
        hwCposLpIfIndex 
            InterfaceIndex,
        hwCposLpId 
            Integer32,
        hwCposFlagJ2Mode 
            INTEGER,
        hwCposFlagJ2Value 
            Integer32,
        hwCposFlagJ2Trace 
            OCTET STRING,
        hwCposRxJ2Mode 
            INTEGER,
        hwCposRxJ2Value 
            Integer32,
        hwCposRxJ2Trace 
            OCTET STRING
        }


    hwCposLpIfIndex OBJECT-TYPE
        SYNTAX InterfaceIndex 
        MAX-ACCESS not-accessible
        STATUS current
        DESCRIPTION
            "Description."
        ::= { hwCposLpEntry 1 }


    hwCposLpId OBJECT-TYPE
        SYNTAX Integer32 
        MAX-ACCESS not-accessible
        STATUS current
        DESCRIPTION
            "Description."
        ::= { hwCposLpEntry 2 }


    hwCposFlagJ2Mode OBJECT-TYPE
        SYNTAX INTEGER {j21ByteMode(1),j216ByteMode(2)}
        MAX-ACCESS read-write
        STATUS current
        DESCRIPTION
            "Description."
        ::= { hwCposLpEntry 3 }


    hwCposFlagJ2Value OBJECT-TYPE
        SYNTAX Integer32 (0..127)
        MAX-ACCESS read-write
        STATUS current
        DESCRIPTION
            "Description."
        ::= { hwCposLpEntry 4 }


    hwCposFlagJ2Trace OBJECT-TYPE
        SYNTAX OCTET STRING (SIZE (0..16))
        MAX-ACCESS read-write
        STATUS current
        DESCRIPTION
            "Description."
        ::= { hwCposLpEntry 5 }


    hwCposRxJ2Mode OBJECT-TYPE
        SYNTAX INTEGER {j21ByteMode(1),j216ByteMode(2)}
        MAX-ACCESS read-only
        STATUS current
        DESCRIPTION
            "Indicates the received J2 mode."
        ::= { hwCposLpEntry 6 }


    hwCposRxJ2Value OBJECT-TYPE
        SYNTAX Integer32 (0..127)
        MAX-ACCESS read-only
        STATUS current
        DESCRIPTION
            "Indicates the received J2 value of 1-byte mode."
        ::= { hwCposLpEntry 7 }


    hwCposRxJ2Trace OBJECT-TYPE
        SYNTAX OCTET STRING (SIZE (0..16))
        MAX-ACCESS read-only
        STATUS current
        DESCRIPTION
            "Indicates the received J2 characters of 16-byte or 64-byte mode."
        ::= { hwCposLpEntry 8 }


    hwDs0ChannelBundle OBJECT IDENTIFIER ::= { hwPortMIBObjects 4 }

    hwDs0ChannelBundleTable OBJECT-TYPE
        SYNTAX  SEQUENCE OF HwDs0ChannelBundleEntry
        MAX-ACCESS not-accessible
        STATUS current
        DESCRIPTION
            "This table is used to bundle timeslots of CE1/CT1 interfaces."
        ::= { hwDs0ChannelBundle 1 }


    hwDs0ChannelBundleEntry OBJECT-TYPE
        SYNTAX HwDs0ChannelBundleEntry 
        MAX-ACCESS not-accessible
        STATUS current
        DESCRIPTION
            "This table is used to bundle timeslots of CE1/CT1 interfaces."
        INDEX { hwDs0ChannelBundleParentIfIndex,hwDs0ChannelBundleDs1ChannelId,hwDs0ChannelBundleId }
        ::= { hwDs0ChannelBundleTable 1 }


    HwDs0ChannelBundleEntry ::= SEQUENCE {
        hwDs0ChannelBundleParentIfIndex 
            InterfaceIndex,
        hwDs0ChannelBundleDs1ChannelId 
            Integer32,
        hwDs0ChannelBundleId 
            Integer32,
        hwDs0ChannelBundleIfIndex 
            InterfaceIndex,
        hwDs0ChannelBundleTimeSlots 
            OCTET STRING,
        hwDs0ChannelBundleSpeed 
            INTEGER,
        hwDs0ChannelBundleTimeSlot0 
            TruthValue,
        hwDs0ChannelBundleIsMasterPW 
            INTEGER,
        hwDs0ChannelBundleMasterPWStatus 
            INTEGER,
        hwDs0ChannelBundlePortName 
            OCTET STRING,
        hwDs0ChannelBundleRowStatus 
            RowStatus
        }


    hwDs0ChannelBundleParentIfIndex OBJECT-TYPE
        SYNTAX InterfaceIndex 
        MAX-ACCESS accessible-for-notify
        STATUS current
        DESCRIPTION
            "Indicates the index of the parent interface."
        ::= { hwDs0ChannelBundleEntry 1 }


    hwDs0ChannelBundleDs1ChannelId OBJECT-TYPE
        SYNTAX Integer32 
        MAX-ACCESS accessible-for-notify
        STATUS current
        DESCRIPTION
            "Indicates the channel ID."
        ::= { hwDs0ChannelBundleEntry 2 }


    hwDs0ChannelBundleId OBJECT-TYPE
        SYNTAX Integer32 (0..30)
        MAX-ACCESS accessible-for-notify
        STATUS current
        DESCRIPTION
            "Indicates the index number of the channel set."
        ::= { hwDs0ChannelBundleEntry 3 }


    hwDs0ChannelBundleIfIndex OBJECT-TYPE
        SYNTAX InterfaceIndex 
        MAX-ACCESS read-create
        STATUS current
        DESCRIPTION
            "Indicates the index of the serial interface formed by the timeslot binding."
        ::= { hwDs0ChannelBundleEntry 11 }


    hwDs0ChannelBundleTimeSlots OBJECT-TYPE
        SYNTAX OCTET STRING (SIZE (0..61))
        MAX-ACCESS read-create
        STATUS current
        DESCRIPTION
            "Indicates the number of the range of the timeslot to be bound.
                The value is an integer ranging from 0 to 31. Multiple timeslots are
                separated by ','. The range of timeslot is expressed by using '-'.
                For E1 card mode:
                If the timeslots are '0-31', it means unframed format,
                If the timeslots are '0-30', it means framed format,
                For T1 card mode:
                If the timeslots are '0-23', it means unframed format,
                If the timeslots are '0-22', it means framed format,
                and hwDs0ChannelBundleDs1ChannelId and hwDs0ChannelBundleId should be zero."
        ::= { hwDs0ChannelBundleEntry 12 }


    hwDs0ChannelBundleSpeed OBJECT-TYPE
        SYNTAX INTEGER {s56(1),s64(2),s150336(3)}
        UNITS "kilo bytes"
        MAX-ACCESS read-create
        STATUS current
        DESCRIPTION
            "Configures the mode to configure the timeslots.
                If the parameter 56 k is selected, the timeslots are bound in the mode of N x 56 kbit/s.
                If the parameter 64 k is selected, the timeslots are bound in the mode of N x 64 kbit/s.
                If the parameter 150336 k is selected, the interface is used for remarking the CEP interface.
                The default value is 64kbit/s."
        DEFVAL { 64 }
        ::= { hwDs0ChannelBundleEntry 13 }


    hwDs0ChannelBundleTimeSlot0 OBJECT-TYPE
        SYNTAX TruthValue 
        MAX-ACCESS read-create
        STATUS current
        DESCRIPTION
            "Indicates the timeslot0 to be bound or a single channel.
                The ture value indicates it will be create TDM channel."
        ::= { hwDs0ChannelBundleEntry 14 }


    hwDs0ChannelBundleIsMasterPW OBJECT-TYPE
        SYNTAX INTEGER {notacrpw(0),masterpw(1),notmasterpw(2)}
        MAX-ACCESS read-only
        STATUS current
        DESCRIPTION
            "Indicates if the pw configed on this port is master pw."
        DEFVAL { 0 }
        ::= { hwDs0ChannelBundleEntry 15 }


    hwDs0ChannelBundleMasterPWStatus OBJECT-TYPE
        SYNTAX INTEGER {unlock(0),lock(1)}
        MAX-ACCESS read-only
        STATUS current
        DESCRIPTION
            "Indicates the status of master pw."
        DEFVAL { 0 }
        ::= { hwDs0ChannelBundleEntry 16 }


    hwDs0ChannelBundlePortName OBJECT-TYPE
        SYNTAX OCTET STRING 
        MAX-ACCESS read-only
        STATUS current
        DESCRIPTION
            "Port name."
        ::= { hwDs0ChannelBundleEntry 17 }


    hwDs0ChannelBundleRowStatus OBJECT-TYPE
        SYNTAX RowStatus 
        MAX-ACCESS read-create
        STATUS current
        DESCRIPTION
            "This variable is used to create or delete an object."
        ::= { hwDs0ChannelBundleEntry 51 }


    hwDs1 OBJECT IDENTIFIER ::= { hwPortMIBObjects 5 }

    hwDs1Table OBJECT-TYPE
        SYNTAX  SEQUENCE OF HwDs1Entry
        MAX-ACCESS not-accessible
        STATUS current
        DESCRIPTION
            "This table lists all E1/CE1 interfaces or T1/CT1 interfaces.
                After the mode of E3/CE3 interfaces or T3/CT3 interfaces is set to channelized, this table can be used
                to create E1/CE1, or T1/CT1, or E3/CE3, or T3/CT3 interfaces."
        ::= { hwDs1 1 }


    hwDs1Entry OBJECT-TYPE
        SYNTAX HwDs1Entry 
        MAX-ACCESS not-accessible
        STATUS current
        DESCRIPTION
            "This table lists all E1/CE1 interfaces or T1/CT1 interfaces.
                After the mode of E3/CE3 interfaces or T3/CT3 interfaces is set to channelized, this table can be used
                to create E1/CE1, or T1/CT1, or E3/CE3, or T3/CT3 interfaces."
        INDEX { hwDs1ParentIfIndex,hwDs1ChannelId,hwDs1IfIndex }
        ::= { hwDs1Table 1 }


    HwDs1Entry ::= SEQUENCE {
        hwDs1ParentIfIndex 
            InterfaceIndex,
        hwDs1ChannelId 
            Integer32,
        hwDs1IfIndex 
            InterfaceIndex,
        hwDs1ChannelType 
            INTEGER,
        hwDs1IfType 
            INTEGER,
        hwDs1Channelized 
            TruthValue,
        hwDs1CodeType 
            INTEGER,
        hwDs1Clock 
            INTEGER,
        hwDs1FrameFormat 
            INTEGER,
        hwDs1Cable 
            INTEGER,
        hwDs1Loopback 
            INTEGER,
        hwDs1ClockRecoveryDomain 
            Integer32,
        hwDs1PWClockDomain 
            Integer32,
        hwDs1WorkMode 
            Integer32,
        hwDs1EsAlarmTriggerThreshold 
            Integer32,
        hwDs1EsAlarmResumeThreshold 
            Integer32,
        hwDs1RowStatus 
            RowStatus,
        hwDs1Lbo 
            INTEGER,
        hwDs1CableLength 
            INTEGER
        }


    hwDs1ParentIfIndex OBJECT-TYPE
        SYNTAX InterfaceIndex 
        MAX-ACCESS not-accessible
        STATUS current
        DESCRIPTION
            "Indicates the index of the parent interface."
        ::= { hwDs1Entry 1 }


    hwDs1ChannelId OBJECT-TYPE
        SYNTAX Integer32 (0..63)
        MAX-ACCESS accessible-for-notify
        STATUS current
        DESCRIPTION
            "Indicates the channel ID."
        ::= { hwDs1Entry 2 }


    hwDs1IfIndex OBJECT-TYPE
        SYNTAX InterfaceIndex 
        MAX-ACCESS not-accessible
        STATUS current
        DESCRIPTION
            "Indicates the interface index."
        ::= { hwDs1Entry 3 }


    hwDs1ChannelType OBJECT-TYPE
        SYNTAX INTEGER {t1(1),e1(2)}
        MAX-ACCESS read-create
        STATUS current
        DESCRIPTION
            "Indicates the interface type. The type can be E1/CE1 or T1/CT1."
        ::= { hwDs1Entry 11 }


    hwDs1IfType OBJECT-TYPE
        SYNTAX INTEGER {e3(1),t3(2),cpos(3),atm(4),none(255)}
        MAX-ACCESS read-create
        STATUS current
        DESCRIPTION
            "Indicates the interface tyep.
                e3: is multiplexed by CE3 interfaces.
                t3: is multiplexed by CT3 interfaces.
                cpos: is multiplexed by CPOS interfaces.
                atm: is multiplexed by ATM interfaces.
                none: indicates the physical interface.

                default:none"
        DEFVAL { none }
        ::= { hwDs1Entry 12 }


    hwDs1Channelized OBJECT-TYPE
        SYNTAX TruthValue 
        MAX-ACCESS read-create
        STATUS current
        DESCRIPTION
            "Indicates the working mode of the interface.
                true: indicates the channelized mode.
                false: indicates the clear channel mode.
                The default is true."
        DEFVAL { true }
        ::= { hwDs1Entry 13 }


    hwDs1CodeType OBJECT-TYPE
        SYNTAX INTEGER {ami(1),hdb3(2),b8zs(3),none(255)}
        MAX-ACCESS read-create
        STATUS current
        DESCRIPTION
            "Indicates the code type of the interface.
                ami: is short for Alternate Mark Inversion.
                hdb3: is short for High Density Bipolar of Order 3.
                b8zs: is short for Bipolar with 8-Zero Substitution.
                none: is not supported"
        DEFVAL { hdb3 }
        ::= { hwDs1Entry 14 }


    hwDs1Clock OBJECT-TYPE
        SYNTAX INTEGER {master(1),slave(2)}
        MAX-ACCESS read-create
        STATUS current
        DESCRIPTION
            "Indicates the clock mode of the interface.
                master: indicates that the clock works in master mode and uses the internal clock signal.
                slave: indicates that the clock works in slave mode and uses the line clock signal."
        ::= { hwDs1Entry 15 }


    hwDs1FrameFormat OBJECT-TYPE
        SYNTAX INTEGER {esf(1),sf(2),noCrc4(3),crc(4)}
        MAX-ACCESS read-create
        STATUS current
        DESCRIPTION
            "Indicates the frame format of the interface.
                crc4: indicates that the frame format is CRC4.
                no-crc4: indicates that the frame format is no-CRC4.
                sf: indicates that the frame format is Super Frame.
                esf: indicates that the frame format is Extended Super Frame.
                By default, the frame format of an E1 interface is no-crc4.
                By default, the frame format of a T1 interface is esf."
        ::= { hwDs1Entry 16 }


    hwDs1Cable OBJECT-TYPE
        SYNTAX INTEGER {long(1),short(2),none(255)}
        MAX-ACCESS read-create
        STATUS current
        DESCRIPTION
            "The cable command takes effect only if the E1 interface card uses 75-ohm coaxial cable.
                The default is short. If no cable is connected, this parameter is displayed as null."
        DEFVAL { short }
        ::= { hwDs1Entry 17 }


    hwDs1Loopback OBJECT-TYPE
        SYNTAX INTEGER {local(1),remote(2),payload(3),cell(4),none(255)}
        MAX-ACCESS read-create
        STATUS current
        DESCRIPTION
            "Enable the loopback function of the interface.
                local: enables the local loopback on the interface.
                remote: enables the remote loopback on the interface.
                payload: enables the remote payload loopback on the interface.
                cell: enables the local cell loopback. The local cell loopback is used to test the local physical chip."
        DEFVAL { none }
        ::= { hwDs1Entry 18 }


    hwDs1ClockRecoveryDomain OBJECT-TYPE
        SYNTAX Integer32 (0..8)
        MAX-ACCESS read-create
        STATUS current
        DESCRIPTION
            "Indicates the clock recovery domain of the interface."
        DEFVAL { 0 }
        ::= { hwDs1Entry 19 }


    hwDs1PWClockDomain OBJECT-TYPE
        SYNTAX Integer32 (0..8)
        MAX-ACCESS read-create
        STATUS current
        DESCRIPTION
            "Indicates the clock recovery domain of the interface."
        DEFVAL { 0 }
        ::= { hwDs1Entry 20 }


    hwDs1WorkMode OBJECT-TYPE
        SYNTAX Integer32 (0..8)
        MAX-ACCESS read-only
        STATUS current
        DESCRIPTION
            "Indicates the clock recovery domain of the interface."
        DEFVAL { 0 }
        ::= { hwDs1Entry 21 }


    hwDs1EsAlarmTriggerThreshold OBJECT-TYPE
        SYNTAX Integer32 (1..900)
        MAX-ACCESS read-write
        STATUS current
        DESCRIPTION
            "The trigger threshold of code violation count threshold crossing alarm of E1 line side ."
        DEFVAL { 65 }
        ::= { hwDs1Entry 22 }


    hwDs1EsAlarmResumeThreshold OBJECT-TYPE
        SYNTAX Integer32 (1..900)
        MAX-ACCESS read-write
        STATUS current
        DESCRIPTION
            "The resume threshold of code violation count threshold crossing alarm of E1 line side ."
        DEFVAL { 30 }
        ::= { hwDs1Entry 23 }


    hwDs1RowStatus OBJECT-TYPE
        SYNTAX RowStatus 
        MAX-ACCESS read-create
        STATUS current
        DESCRIPTION
            "This variable is used to create or delete an object."
        ::= { hwDs1Entry 51 }


    hwDs1Lbo OBJECT-TYPE
        SYNTAX INTEGER {db75(1),db155(2),db225(3),none(4),notsupport(5)}
        MAX-ACCESS read-create
        STATUS current
        DESCRIPTION
            "The lbo of T1 port. Unit: db. the value is expanded 10 times,so the real value should be reduced 10 times"
        ::= { hwDs1Entry 52 }


    hwDs1CableLength OBJECT-TYPE
        SYNTAX INTEGER {length133(1),length266(2),length399(3),length533(4),length655(5),notsupport(6),none(255)}
        MAX-ACCESS read-create
        STATUS current
        DESCRIPTION
            "The cableLength of T1 port. Unit: feet."
        ::= { hwDs1Entry 53 }


    hwDs3 OBJECT IDENTIFIER ::= { hwPortMIBObjects 6 }

    hwDs3Table OBJECT-TYPE
        SYNTAX  SEQUENCE OF HwDs3Entry
        MAX-ACCESS not-accessible
        STATUS current
        DESCRIPTION
            "This table lists all E3/CE3 interfaces or all T3/CT3 interfaces."
        ::= { hwDs3 1 }


    hwDs3Entry OBJECT-TYPE
        SYNTAX HwDs3Entry 
        MAX-ACCESS not-accessible
        STATUS current
        DESCRIPTION
            "This table lists all E3/CE3 interfaces or all T3/CT3 interfaces."
        INDEX { hwDs3ParentIfIndex,hwDs3ChannelId,hwDs3IfIndex }
        ::= { hwDs3Table 1 }


    HwDs3Entry ::= SEQUENCE {
        hwDs3ParentIfIndex 
            InterfaceIndex,
        hwDs3ChannelId 
            Integer32,
        hwDs3IfIndex 
            InterfaceIndex,
        hwDs3ChannelType 
            INTEGER,
        hwDs3IfType 
            INTEGER,
        hwDs3Channelized 
            TruthValue,
        hwDs3Clock 
            INTEGER,
        hwDs3FrameFormat 
            INTEGER,
        hwDs3Scramble 
            TruthValue,
        hwDs3Cable 
            INTEGER,
        hwDs3NationalBit 
            INTEGER,
        hwDs3Loopback 
            INTEGER,
        hwDs3CreateSerial 
            TruthValue,
        hwDs3RowStatus 
            RowStatus
        }


    hwDs3ParentIfIndex OBJECT-TYPE
        SYNTAX InterfaceIndex 
        MAX-ACCESS not-accessible
        STATUS current
        DESCRIPTION
            "Indicates the index of the parent interface."
        ::= { hwDs3Entry 1 }


    hwDs3ChannelId OBJECT-TYPE
        SYNTAX Integer32 (0..3)
        MAX-ACCESS not-accessible
        STATUS current
        DESCRIPTION
            "Indicates the index of the parent interface."
        ::= { hwDs3Entry 2 }


    hwDs3IfIndex OBJECT-TYPE
        SYNTAX InterfaceIndex 
        MAX-ACCESS not-accessible
        STATUS current
        DESCRIPTION
            "Indicates the interface index."
        ::= { hwDs3Entry 3 }


    hwDs3ChannelType OBJECT-TYPE
        SYNTAX INTEGER {t3(1),e3(2)}
        MAX-ACCESS read-create
        STATUS current
        DESCRIPTION
            "Indicates the interface type. The type can be E3/CE3 or T3/CT3."
        ::= { hwDs3Entry 11 }


    hwDs3IfType OBJECT-TYPE
        SYNTAX INTEGER {cpos(1),none(255)}
        MAX-ACCESS read-create
        STATUS current
        DESCRIPTION
            "Indicates the parent interface type of the interface.
                cpos: is multiplexed by CPOS interfaces.
                none: indicates the interface is a physical interface.
                The default is none."
        DEFVAL { none }
        ::= { hwDs3Entry 12 }


    hwDs3Channelized OBJECT-TYPE
        SYNTAX TruthValue 
        MAX-ACCESS read-create
        STATUS current
        DESCRIPTION
            "Indicates the working mode of the interface.
                true: indicates the channelized mode.
                false: indicates the clear channel mode.
                The default is true."
        DEFVAL { true }
        ::= { hwDs3Entry 13 }


    hwDs3Clock OBJECT-TYPE
        SYNTAX INTEGER {master(1),slave(2)}
        MAX-ACCESS read-create
        STATUS current
        DESCRIPTION
            "Indicates the clock mode of the interface.
                master: indicates that the clock works in master mode and uses the internal clock signal.
                slave: indicates that the clock works in slave mode and uses the line clock signal."
        ::= { hwDs3Entry 14 }


    hwDs3FrameFormat OBJECT-TYPE
        SYNTAX INTEGER {g832Adm(1),g751Adm(2),g751Plcp(3),cbitAdm(4),cbitPlcp(5),m23Adm(6),m23Plcp(7)}
        MAX-ACCESS read-create
        STATUS current
        DESCRIPTION
            "Indicates the frame format of the interface."
        ::= { hwDs3Entry 15 }


    hwDs3Scramble OBJECT-TYPE
        SYNTAX TruthValue 
        MAX-ACCESS read-create
        STATUS current
        DESCRIPTION
            "Indicates the scramble function of the interface.
                true: enables the scramble function.
                false: disables the scramble function.
                The default is false."
        DEFVAL { false }
        ::= { hwDs3Entry 16 }


    hwDs3Cable OBJECT-TYPE
        SYNTAX INTEGER {long(1),short(2)}
        MAX-ACCESS read-create
        STATUS current
        DESCRIPTION
            "The cable command takes effect only if the E3 interface card uses 75-ohm coaxial cable.
                The default is short. If no cable is connected, this parameter is displayed as null."
        DEFVAL { short }
        ::= { hwDs3Entry 17 }


    hwDs3NationalBit OBJECT-TYPE
        SYNTAX INTEGER {n0(1),n1(2)}
        MAX-ACCESS read-create
        STATUS current
        DESCRIPTION
            "Indicates the national bit of the E3/CE3 interface.
                n0: indicates the national bit is 0 and the interface supports only the communication within a country.
                n1: indicates the national bit is 1 and the interface supports the international communication.  "
        DEFVAL { n0 }
        ::= { hwDs3Entry 18 }


    hwDs3Loopback OBJECT-TYPE
        SYNTAX INTEGER {local(1),remote(2),payload(3),cell(4),none(255)}
        MAX-ACCESS read-create
        STATUS current
        DESCRIPTION
            "Enable the loopback function of the interface.
                local: enables the local loopback on the interface.
                remote: enables the remote loopback on the interface.
                payload: enables the remote payload loopback on the interface.
                cell: enables the local cell loopback. The local cell loopback is used to test the local physical chip."
        DEFVAL { none }
        ::= { hwDs3Entry 19 }


    hwDs3CreateSerial OBJECT-TYPE
        SYNTAX TruthValue 
        MAX-ACCESS read-create
        STATUS current
        DESCRIPTION
            "Create serial interface from Ds3 interface.
                True create serial interface.
                False  destroy serial interface.
                 "
        DEFVAL { false }
        ::= { hwDs3Entry 20 }


    hwDs3RowStatus OBJECT-TYPE
        SYNTAX RowStatus 
        MAX-ACCESS read-create
        STATUS current
        DESCRIPTION
            "This variable is used to create or delete an object."
        ::= { hwDs3Entry 51 }


    hwBundleSerial OBJECT IDENTIFIER ::= { hwPortMIBObjects 7 }

    hwBundleSerialTable OBJECT-TYPE
        SYNTAX  SEQUENCE OF HwBundleSerialEntry
        MAX-ACCESS not-accessible
        STATUS current
        DESCRIPTION
            "Indicates the attribute of the serial interface formed by timeslots.
                This table lists the physical attributes of the serial interface."
        ::= { hwBundleSerial 1 }


    hwBundleSerialEntry OBJECT-TYPE
        SYNTAX HwBundleSerialEntry 
        MAX-ACCESS not-accessible
        STATUS current
        DESCRIPTION
            "Indicates the attribute of the serial interface formed by timeslots.
                This table lists the physical attributes of the serial interface."
        INDEX { hwBundleSerialIfIndex }
        ::= { hwBundleSerialTable 1 }


    HwBundleSerialEntry ::= SEQUENCE {
        hwBundleSerialIfIndex 
            InterfaceIndex,
        hwBundleSerialLinkProtocol 
            INTEGER,
        hwBundleSerialTimerHold 
            Integer32,
        hwBundleSerialLoopback 
            TruthValue,
        hwBundleSerialCrcVerifyCode 
            INTEGER
        }


    hwBundleSerialIfIndex OBJECT-TYPE
        SYNTAX InterfaceIndex 
        MAX-ACCESS not-accessible
        STATUS current
        DESCRIPTION
            "Interface index(es) of serial(s) present on the device ."
        ::= { hwBundleSerialEntry 1 }


    hwBundleSerialLinkProtocol OBJECT-TYPE
        SYNTAX INTEGER {ietf(1),nonstandard(2),hdlc(3),ppp(4),lapb(5),atm(6),tdm(7),none(255)}
        MAX-ACCESS read-write
        STATUS current
        DESCRIPTION
            "The link-protocol of interface. The serial(s) always use PPP as its link-protocol for default."
        ::= { hwBundleSerialEntry 11 }


    hwBundleSerialTimerHold OBJECT-TYPE
        SYNTAX Integer32 (0..32767)
        MAX-ACCESS read-write
        STATUS current
        DESCRIPTION
            "Indicates the interval for sending Keepalive packets from the serial interface to the peer.
                The default is 10 seconds."
        ::= { hwBundleSerialEntry 12 }


    hwBundleSerialLoopback OBJECT-TYPE
        SYNTAX TruthValue 
        MAX-ACCESS read-write
        STATUS current
        DESCRIPTION
            "true: enables the loopback on the serial interface.
                false: disables the loopback on the serial interface.
                By default, the loopback on the serial interface is disabled."
        DEFVAL { false }
        ::= { hwBundleSerialEntry 13 }


    hwBundleSerialCrcVerifyCode OBJECT-TYPE
        SYNTAX INTEGER {crc16(1),crc32(2)}
        MAX-ACCESS read-write
        STATUS current
        DESCRIPTION
            "Indicates the length of the CRC verify code. The default is 32."
        ::= { hwBundleSerialEntry 14 }


    hwPhysicalPort OBJECT IDENTIFIER ::= { hwPortMIBObjects 8 }

    hwPhysicalPortTable OBJECT-TYPE
        SYNTAX  SEQUENCE OF HwPhysicalPortEntry
        MAX-ACCESS not-accessible
        STATUS current
        DESCRIPTION
            "This table describes the access and configuration of attributes of various physical interfaces."
        ::= { hwPhysicalPort 1 }


    hwPhysicalPortEntry OBJECT-TYPE
        SYNTAX HwPhysicalPortEntry 
        MAX-ACCESS not-accessible
        STATUS current
        DESCRIPTION
            "Indicates the attribute of the physical port."
        INDEX { hwPhysicalPortIfIndex }
        ::= { hwPhysicalPortTable 1 }


    HwPhysicalPortEntry ::= SEQUENCE {
        hwPhysicalPortIfIndex 
            InterfaceIndex,
        hwPhysicalPortDelayTime 
            Unsigned32,
        hwPhysicalPortDelayRemainTime 
            Unsigned32,
        hwPhysicalPortName 
            OCTET STRING,
        hwPhysicalPortInChassis 
            Integer32,
        hwPhysicalPortInSlot 
            Integer32,
        hwPhysicalPortInCard 
            Integer32,
        hwPhysicalPortInPort 
            Integer32,
        hwPhysicalAutoShutLaserEnable 
            INTEGER,
        hwPhysicalAutoShutLaserOpenInterval 
            Integer32,
        hwPhysicalAutoShutLaserCloseInterval 
            Integer32,
        hwPhysicalAutoShutLaserLongOpenInterval 
            Integer32,
        hwPhysicalLoopbackType 
            INTEGER,
        hwPhysicalShutLaser 
            INTEGER,
        hwPhysicalLaserStatus 
            INTEGER,
        hwPhysicalPortHoldUp 
            INTEGER,
        hwPhysicalPortAlarmInverseEnable 
            INTEGER,
        hwPhysicalPortInVsId 
            Integer32,
        hwPhysicalPortAlarmName 
            OCTET STRING,
        hwInputRateChangeThresholdPercent
            Integer32,
        hwOutputRateChangeThresholdPercent
            Integer32,
	hwCurrentStatisticalPeriodRate
	    Counter64,
	hwLastStatisticalPeriodRate
	    Counter64,
        hwPortPhysicalRate
            Integer32,
        hwLicenseType
	    OCTET STRING,
	hwMaxPortNum
	    Integer32,
	hwUsedPortNum
	    Integer32,
	hwPhysicalPortMode
	    INTEGER,
	hwScadaGroupId
	    Integer32,
    hwPhysicalPortGroupID
             OCTET STRING,
        hwPortTransModeReasonDescr 			
            OCTET STRING,
	hwAcBlockReason
            OCTET STRING,
        hwPhysicalPortLocalPhyNum	
            OCTET STRING,
        hwPhysicalPortRemotePhyNum
            OCTET STRING,
        hwPhysicalPortLocalGroupID
            Integer32,
        hwPhysicalPortRemteGroupID
            Integer32,
        hwPhysicalPortBW
            OCTET STRING,
        hwPhysicalPortList    
            OCTET STRING,
        hwPhysicalPortPortType
            Integer32,
        hwPhysicalPortAlarmReason 
            Integer32
        }


    hwPhysicalPortIfIndex OBJECT-TYPE
        SYNTAX InterfaceIndex 
        MAX-ACCESS accessible-for-notify
        STATUS current
        DESCRIPTION
            "This object indicates the interface index."
        ::= { hwPhysicalPortEntry 1 }


    hwPhysicalPortDelayTime OBJECT-TYPE
        SYNTAX Unsigned32 (0..86400000)
        MAX-ACCESS read-write
        STATUS current
        DESCRIPTION
            "This object indicates the interface delay. The default value is 0 ms."
        DEFVAL { 0 }
        ::= { hwPhysicalPortEntry 2 }


    hwPhysicalPortDelayRemainTime OBJECT-TYPE
        SYNTAX Unsigned32 (0..86400000)
        MAX-ACCESS read-only
        STATUS current
        DESCRIPTION
            "This object indicates the remaining time after the interface delay is enabled. The value is in milliseconds."
        ::= { hwPhysicalPortEntry 3 }


    hwPhysicalPortName OBJECT-TYPE
        SYNTAX OCTET STRING 
        MAX-ACCESS read-only
        STATUS current
        DESCRIPTION
            "Indicates the physical port name."
        ::= { hwPhysicalPortEntry 4 }


    hwPhysicalPortInChassis OBJECT-TYPE
        SYNTAX Integer32 
        MAX-ACCESS read-only
        STATUS current
        DESCRIPTION
            "Indicates the physical port in chassis."
        ::= { hwPhysicalPortEntry 5 }


    hwPhysicalPortInSlot OBJECT-TYPE
        SYNTAX Integer32 
        MAX-ACCESS read-only
        STATUS current
        DESCRIPTION
            "Indicates the SlotID."
        ::= { hwPhysicalPortEntry 6 }


    hwPhysicalPortInCard OBJECT-TYPE
        SYNTAX Integer32 
        MAX-ACCESS read-only
        STATUS current
        DESCRIPTION
            "Indicates the CardID."
        ::= { hwPhysicalPortEntry 7 }


    hwPhysicalPortInPort OBJECT-TYPE
        SYNTAX Integer32 
        MAX-ACCESS read-only
        STATUS current
        DESCRIPTION
            "Indicates the PortID."
        ::= { hwPhysicalPortEntry 8 }


    hwPhysicalAutoShutLaserEnable OBJECT-TYPE
        SYNTAX INTEGER {enable(1),disable(2),notsupport(255)}
        MAX-ACCESS read-write
        STATUS current
        DESCRIPTION
            "This object indicates the automatic disabling of LASER. By default, automatic disabling of LASER is not supported."
        ::= { hwPhysicalPortEntry 9 }


    hwPhysicalAutoShutLaserOpenInterval OBJECT-TYPE
        SYNTAX Integer32 (100..300 | 2147483647)
        MAX-ACCESS read-write
        STATUS current
        DESCRIPTION
            "This object indicates the enabling interval for the automatic disabling of LASER. The default value is 2000 ms. The value 2147483647 indicates that the interface does not support this function."
        ::= { hwPhysicalPortEntry 10 }


    hwPhysicalAutoShutLaserCloseInterval OBJECT-TYPE
        SYNTAX Integer32 (200..30000 | 2147483647)
        MAX-ACCESS read-write
        STATUS current
        DESCRIPTION
            "This object indicates the disabling interval for the automatic disabling of LASER. The default value is 60000 ms. The value 2147483647 indicates that the interface does not support this function."
        ::= { hwPhysicalPortEntry 11 }


    hwPhysicalAutoShutLaserLongOpenInterval OBJECT-TYPE
        SYNTAX Integer32 (200..30000 | 2147483647)
        MAX-ACCESS read-write
        STATUS current
        DESCRIPTION
            "This object indicates the long enabling interval for the automatic disabling of LASER. The default value is 90000 ms. The value 2147483647 indicates that the interface does not support this function."
        ::= { hwPhysicalPortEntry 12 }


    hwPhysicalLoopbackType OBJECT-TYPE
        SYNTAX INTEGER {stopLoopback(0),local(1),remote(2)}
        MAX-ACCESS read-only
        STATUS current
        DESCRIPTION
            "This object indicates the current interface status."
        ::= { hwPhysicalPortEntry 13 }


    hwPhysicalShutLaser OBJECT-TYPE
        SYNTAX INTEGER {off(1),on(2),notsupport(255)}
        MAX-ACCESS read-write
        STATUS current
        DESCRIPTION
            "This object indicates whether the LASER function is enabled or not."
        ::= { hwPhysicalPortEntry 14 }


    hwPhysicalLaserStatus OBJECT-TYPE
        SYNTAX INTEGER {off(1),on(2),offline(3),notsupport(255)}
        MAX-ACCESS read-only
        STATUS current
        DESCRIPTION
            "This object indicates the LASER status."
        ::= { hwPhysicalPortEntry 15 }


    hwPhysicalPortHoldUp OBJECT-TYPE
        SYNTAX INTEGER {disable(0),enable(1)}
        MAX-ACCESS read-write
        STATUS current
        DESCRIPTION
            "This object indicates whether the interface is Up."
        ::= { hwPhysicalPortEntry 16 }


    hwPhysicalPortAlarmInverseEnable OBJECT-TYPE
        SYNTAX INTEGER {enable(1),disable(2)}
        MAX-ACCESS read-write
        STATUS current
        DESCRIPTION
            "Config port alarm inverse enable."
        ::= { hwPhysicalPortEntry 17 }


    hwPhysicalPortInVsId OBJECT-TYPE
        SYNTAX Integer32 
        MAX-ACCESS read-only
        STATUS current
        DESCRIPTION
            "VsId."
        ::= { hwPhysicalPortEntry 18 }


    hwPhysicalPortAlarmName OBJECT-TYPE
        SYNTAX OCTET STRING 
        MAX-ACCESS read-only
        STATUS current
        DESCRIPTION
            "Indicates the physical port alarm name."
        ::= { hwPhysicalPortEntry 19 } 


    hwInputRateChangeThresholdPercent OBJECT-TYPE
        SYNTAX Integer32 
        MAX-ACCESS read-write
        STATUS current
        DESCRIPTION
            "Indicates the threshold for the input rate change, in percentage."
        ::= { hwPhysicalPortEntry 20 } 


    hwOutputRateChangeThresholdPercent OBJECT-TYPE
        SYNTAX Integer32 
        MAX-ACCESS read-write
        STATUS current
        DESCRIPTION
            "Indicates the threshold for the output rate change, in percentage."
        ::= { hwPhysicalPortEntry 21 } 


    hwCurrentStatisticalPeriodRate OBJECT-TYPE
        SYNTAX Counter64 
        MAX-ACCESS read-only
        STATUS current
        DESCRIPTION
            "Indicates the rate in the current statistical period."
        ::= { hwPhysicalPortEntry 22 } 


    hwLastStatisticalPeriodRate OBJECT-TYPE
        SYNTAX Counter64 
        MAX-ACCESS read-only
        STATUS current
        DESCRIPTION
            "Indicates the rate in the last statistical period."
        ::= { hwPhysicalPortEntry 23 }
	
     hwPortPhysicalRate OBJECT-TYPE
        SYNTAX Integer32 
        MAX-ACCESS read-only
        STATUS current
        DESCRIPTION
            "Indicates the current physical rate."
        ::= { hwPhysicalPortEntry 24 }  

		-- 1.3.6.1.4.1.2011.5.25.157.1.8.1.1.25
		hwLicenseType OBJECT-TYPE
			SYNTAX OCTET STRING
			MAX-ACCESS read-only
			STATUS current
			DESCRIPTION
				"Indicates the type of interface function-controlled license."
			::= { hwPhysicalPortEntry 25 }

		-- 1.3.6.1.4.1.2011.5.25.157.1.8.1.1.26
		hwMaxPortNum OBJECT-TYPE
			SYNTAX Integer32
			MAX-ACCESS read-only
			STATUS current
			DESCRIPTION
				"Indicates the Maximum number of available interfaces"
			::= { hwPhysicalPortEntry 26 }

		-- 1.3.6.1.4.1.2011.5.25.157.1.8.1.1.27
		hwUsedPortNum OBJECT-TYPE
			SYNTAX Integer32
			MAX-ACCESS read-only
			STATUS current
			DESCRIPTION
				"Indicates the Number of interfaces in use."
			::= { hwPhysicalPortEntry 27 }

    -- 1.3.6.1.4.1.2011.5.25.157.1.8.1.1.28
     hwPhysicalPortMode OBJECT-TYPE
         SYNTAX INTEGER {eth1g(0),eth10g(1)}
         MAX-ACCESS read-only
         STATUS current
         DESCRIPTION
            " The current state of portMode in port."
         ::= { hwPhysicalPortEntry 28 }
		-- 1.3.6.1.4.1.2011.5.25.157.1.8.1.1.29
		hwScadaGroupId OBJECT-TYPE
			SYNTAX Integer32
			MAX-ACCESS read-only
			STATUS current
			DESCRIPTION
				"Indicates the scada group ID."
			::= { hwPhysicalPortEntry 29 }

    -- 1.3.6.1.4.1.2011.5.25.157.1.8.1.1.30
    hwPhysicalPortGroupID OBJECT-TYPE
        SYNTAX OCTET STRING 
        MAX-ACCESS read-only
        STATUS current
        DESCRIPTION
            "Indicates the physical port group ID."
        ::= { hwPhysicalPortEntry 30 } 	
		
    -- 1.3.6.1.4.1.2011.5.25.157.1.8.1.1.31
    hwPortTransModeReasonDescr OBJECT-TYPE
        SYNTAX OCTET STRING 
        MAX-ACCESS read-only
        STATUS current
        DESCRIPTION
            "Indicates the physical port transmission mode different reason."
        ::= { hwPhysicalPortEntry 31 } 	

		-- 1.3.6.1.4.1.2011.5.25.157.1.8.1.1.32
		hwAcBlockReason OBJECT-TYPE
			SYNTAX OCTET STRING
			MAX-ACCESS read-only
			STATUS current
			DESCRIPTION
				"Indicates the AC block reason."
			::= { hwPhysicalPortEntry 32 }

    -- 1.3.6.1.4.1.2011.5.25.157.1.8.1.1.33
    hwPhysicalPortLocalPhyNum OBJECT-TYPE
        SYNTAX OCTET STRING 
        MAX-ACCESS read-only
        STATUS current
        DESCRIPTION
            "Indicates the local physical port phy number."
        ::= { hwPhysicalPortEntry 33 } 		        

    -- 1.3.6.1.4.1.2011.5.25.157.1.8.1.1.34
    hwPhysicalPortRemotePhyNum OBJECT-TYPE
        SYNTAX OCTET STRING 
        MAX-ACCESS read-only
        STATUS current
        DESCRIPTION
            "Indicates the remote physical port phy number."
        ::= { hwPhysicalPortEntry 34 } 	

    -- 1.3.6.1.4.1.2011.5.25.157.1.8.1.1.35
    hwPhysicalPortLocalGroupID OBJECT-TYPE
        SYNTAX Integer32 
        MAX-ACCESS read-only
        STATUS current
        DESCRIPTION
            "Indicates the local physical port groupID."
        ::= { hwPhysicalPortEntry 35 }

    -- 1.3.6.1.4.1.2011.5.25.157.1.8.1.1.36
    hwPhysicalPortRemteGroupID OBJECT-TYPE
        SYNTAX Integer32 
        MAX-ACCESS read-only
        STATUS current
        DESCRIPTION
            "Indicates the remote physical port groupID."
        ::= { hwPhysicalPortEntry 36 }

    -- 1.3.6.1.4.1.2011.5.25.157.1.8.1.1.37
    hwPhysicalPortBW OBJECT-TYPE
        SYNTAX OCTET STRING 
        MAX-ACCESS read-only
        STATUS current
        DESCRIPTION
            "Indicates the local port bandwidth"
        ::= { hwPhysicalPortEntry 37 }
        
    -- 1.3.6.1.4.1.2011.5.25.157.1.8.1.1.38
    hwPhysicalPortList OBJECT-TYPE
        SYNTAX OCTET STRING 
        MAX-ACCESS read-only
        STATUS current
        DESCRIPTION
            "Indicates the physical port list"
        ::= { hwPhysicalPortEntry 38 }  

    -- 1.3.6.1.4.1.2011.5.25.157.1.8.1.1.39
    hwPhysicalPortPortType OBJECT-TYPE
        SYNTAX Integer32 
        MAX-ACCESS read-only
        STATUS current
        DESCRIPTION
            "Indicates the physical port type"
        ::= { hwPhysicalPortEntry 39 }  

    -- 1.3.6.1.4.1.2011.5.25.157.1.8.1.1.40
    hwPhysicalPortAlarmReason OBJECT-TYPE
        SYNTAX Integer32 
        MAX-ACCESS read-only
        STATUS current
        DESCRIPTION
            "Indicates the physical port alarm reason"
        ::= { hwPhysicalPortEntry 40 }        
		
		-- 1.3.6.1.4.1.2011.5.25.157.1.8.2
    hwSDHRsMsPerfCurrentTable OBJECT-TYPE
        SYNTAX  SEQUENCE OF HwSDHRsMsPerfCurrentEntry
        MAX-ACCESS not-accessible
        STATUS current
        DESCRIPTION
            "This table describes functions of physical interfaces."
        ::= { hwPhysicalPort 2 }


    hwSDHRsMsPerfCurrentEntry OBJECT-TYPE
        SYNTAX HwSDHRsMsPerfCurrentEntry 
        MAX-ACCESS not-accessible
        STATUS current
        DESCRIPTION
            "Indicates the performance stat of the Regenerator Section."
        INDEX { hwSDHRsMsPerfCurrentIfIndex,hwSDHRsMsPerfCurrentDataIndex }
        ::= { hwSDHRsMsPerfCurrentTable 1 }


    HwSDHRsMsPerfCurrentEntry ::= SEQUENCE {
        hwSDHRsMsPerfCurrentIfIndex 
            InterfaceIndex,
        hwSDHRsMsPerfCurrentDataIndex 
            Integer32,
        hwSDHRsPerfCurrentBBE 
            Integer32,
        hwSDHRsPerfCurrentES 
            Integer32,
        hwSDHRsPerfCurrentSES 
            Integer32,
        hwSDHRsPerfCurrentUAS 
            Integer32,
        hwSDHMsPerfCurrentBBE 
            Integer32,
        hwSDHMsPerfCurrentES 
            Integer32,
        hwSDHMsPerfCurrentSES 
            Integer32,
        hwSDHMsPerfCurrentUAS 
            Integer32,
        hwSDHMsPerfCurrentFEBBE 
            Integer32,
        hwSDHMsPerfCurrentFEES 
            Integer32,
        hwSDHMsPerfCurrentFESES 
            Integer32,
        hwSDHMsPerfCurrentFEUAS 
            Integer32
        }


    hwSDHRsMsPerfCurrentIfIndex OBJECT-TYPE
        SYNTAX InterfaceIndex 
        MAX-ACCESS not-accessible
        STATUS current
        DESCRIPTION
            "This object indicates the interface index."
        ::= { hwSDHRsMsPerfCurrentEntry 1 }


    hwSDHRsMsPerfCurrentDataIndex OBJECT-TYPE
        SYNTAX Integer32 (0..1)
        MAX-ACCESS not-accessible
        STATUS current
        DESCRIPTION
            "This object indicates the data index."
        ::= { hwSDHRsMsPerfCurrentEntry 2 }


    hwSDHRsPerfCurrentBBE OBJECT-TYPE
        SYNTAX Integer32 
        MAX-ACCESS read-only
        STATUS current
        DESCRIPTION
            "This object indicates the regenerator section (RS) background block error."
        ::= { hwSDHRsMsPerfCurrentEntry 3 }


    hwSDHRsPerfCurrentES OBJECT-TYPE
        SYNTAX Integer32 
        MAX-ACCESS read-only
        STATUS current
        DESCRIPTION
            "This object indicates the number of seconds that the RS error lasts."
        ::= { hwSDHRsMsPerfCurrentEntry 4 }


    hwSDHRsPerfCurrentSES OBJECT-TYPE
        SYNTAX Integer32 
        MAX-ACCESS read-only
        STATUS current
        DESCRIPTION
            "This object indicates the number of seconds that the severe RS error lasts."
        ::= { hwSDHRsMsPerfCurrentEntry 5 }


    hwSDHRsPerfCurrentUAS OBJECT-TYPE
        SYNTAX Integer32 
        MAX-ACCESS read-only
        STATUS current
        DESCRIPTION
            "This object indicates the number of seconds that the RS does not exist."
        ::= { hwSDHRsMsPerfCurrentEntry 6 }


    hwSDHMsPerfCurrentBBE OBJECT-TYPE
        SYNTAX Integer32 
        MAX-ACCESS read-only
        STATUS current
        DESCRIPTION
            "This object indicates the multi-section background block error."
        ::= { hwSDHRsMsPerfCurrentEntry 7 }


    hwSDHMsPerfCurrentES OBJECT-TYPE
        SYNTAX Integer32 
        MAX-ACCESS read-only
        STATUS current
        DESCRIPTION
            "This object indicates the number of seconds that the multi-section error lasts."
        ::= { hwSDHRsMsPerfCurrentEntry 8 }


    hwSDHMsPerfCurrentSES OBJECT-TYPE
        SYNTAX Integer32 
        MAX-ACCESS read-only
        STATUS current
        DESCRIPTION
            "This object indicates the number of seconds that the severe multi-section error lasts."
        ::= { hwSDHRsMsPerfCurrentEntry 9 }


    hwSDHMsPerfCurrentUAS OBJECT-TYPE
        SYNTAX Integer32 
        MAX-ACCESS read-only
        STATUS current
        DESCRIPTION
            "This object indicates the number of seconds that the multi-section does not exist."
        ::= { hwSDHRsMsPerfCurrentEntry 10 }


    hwSDHMsPerfCurrentFEBBE OBJECT-TYPE
        SYNTAX Integer32 
        MAX-ACCESS read-only
        STATUS current
        DESCRIPTION
            "This object indicates the multi-section remote background block error."
        ::= { hwSDHRsMsPerfCurrentEntry 11 }


    hwSDHMsPerfCurrentFEES OBJECT-TYPE
        SYNTAX Integer32 
        MAX-ACCESS read-only
        STATUS current
        DESCRIPTION
            "This object indicates the number of seconds that the multi-section remote error lasts."
        ::= { hwSDHRsMsPerfCurrentEntry 12 }


    hwSDHMsPerfCurrentFESES OBJECT-TYPE
        SYNTAX Integer32 
        MAX-ACCESS read-only
        STATUS current
        DESCRIPTION
            "This object indicates the number of seconds that the severe multi-section remote error lasts."
        ::= { hwSDHRsMsPerfCurrentEntry 13 }


    hwSDHMsPerfCurrentFEUAS OBJECT-TYPE
        SYNTAX Integer32 
        MAX-ACCESS read-only
        STATUS current
        DESCRIPTION
            "This object indicates the number of seconds that the multi-section remote error does not exist."
        ::= { hwSDHRsMsPerfCurrentEntry 14 }


    hwSDHHpPerfCurrentTable OBJECT-TYPE
        SYNTAX  SEQUENCE OF HwSDHHpPerfCurrentEntry
        MAX-ACCESS not-accessible
        STATUS current
        DESCRIPTION
            "This table describes functions of physical interfaces."
        ::= { hwPhysicalPort 3 }


    hwSDHHpPerfCurrentEntry OBJECT-TYPE
        SYNTAX HwSDHHpPerfCurrentEntry 
        MAX-ACCESS not-accessible
        STATUS current
        DESCRIPTION
            "Indicates the performance stat of the Higher order Path."
        INDEX { hwSDHHpPerfCurrentIfIndex,hwSDHHpPerfCurrentHpIndex,hwSDHHpPerfCurrentDataIndex }
        ::= { hwSDHHpPerfCurrentTable 1 }


    HwSDHHpPerfCurrentEntry ::= SEQUENCE {
        hwSDHHpPerfCurrentIfIndex 
            InterfaceIndex,
        hwSDHHpPerfCurrentHpIndex 
            Integer32,
        hwSDHHpPerfCurrentDataIndex 
            Integer32,
        hwSDHHpPerfCurrentBBE 
            Integer32,
        hwSDHHpPerfCurrentES 
            Integer32,
        hwSDHHpPerfCurrentSES 
            Integer32,
        hwSDHHpPerfCurrentUAS 
            Integer32,
        hwSDHHpPerfCurrentFEBBE 
            Integer32,
        hwSDHHpPerfCurrentFEES 
            Integer32,
        hwSDHHpPerfCurrentFESES 
            Integer32,
        hwSDHHpPerfCurrentFEUAS 
            Integer32
        }


    hwSDHHpPerfCurrentIfIndex OBJECT-TYPE
        SYNTAX InterfaceIndex 
        MAX-ACCESS accessible-for-notify
        STATUS current
        DESCRIPTION
            "This object indicates the interface index."
        ::= { hwSDHHpPerfCurrentEntry 1 }


    hwSDHHpPerfCurrentHpIndex OBJECT-TYPE
        SYNTAX Integer32 
        MAX-ACCESS not-accessible
        STATUS current
        DESCRIPTION
            "This object indicates the higher order path (HP) index."
        ::= { hwSDHHpPerfCurrentEntry 2 }


    hwSDHHpPerfCurrentDataIndex OBJECT-TYPE
        SYNTAX Integer32 (0..1)
        MAX-ACCESS not-accessible
        STATUS current
        DESCRIPTION
            "This object indicates the data index."
        ::= { hwSDHHpPerfCurrentEntry 3 }


    hwSDHHpPerfCurrentBBE OBJECT-TYPE
        SYNTAX Integer32 
        MAX-ACCESS read-only
        STATUS current
        DESCRIPTION
            "This object indicates the background errored block of the HP."
        ::= { hwSDHHpPerfCurrentEntry 4 }


    hwSDHHpPerfCurrentES OBJECT-TYPE
        SYNTAX Integer32 
        MAX-ACCESS read-only
        STATUS current
        DESCRIPTION
            "This object indicates the number of errored seconds on the HP."
        ::= { hwSDHHpPerfCurrentEntry 5 }


    hwSDHHpPerfCurrentSES OBJECT-TYPE
        SYNTAX Integer32 
        MAX-ACCESS read-only
        STATUS current
        DESCRIPTION
            "This object indicates the number of severe errored seconds on the HP."
        ::= { hwSDHHpPerfCurrentEntry 6 }


    hwSDHHpPerfCurrentUAS OBJECT-TYPE
        SYNTAX Integer32 
        MAX-ACCESS read-only
        STATUS current
        DESCRIPTION
            "This object indicates the number of unavailable seconds on the HP."
        ::= { hwSDHHpPerfCurrentEntry 7 }


    hwSDHHpPerfCurrentFEBBE OBJECT-TYPE
        SYNTAX Integer32 
        MAX-ACCESS read-only
        STATUS current
        DESCRIPTION
            "This object indicates the remote background errored block on the HP."
        ::= { hwSDHHpPerfCurrentEntry 8 }


    hwSDHHpPerfCurrentFEES OBJECT-TYPE
        SYNTAX Integer32 
        MAX-ACCESS read-only
        STATUS current
        DESCRIPTION
            "This object indicates the number of remote errored seconds on the HP."
        ::= { hwSDHHpPerfCurrentEntry 9 }


    hwSDHHpPerfCurrentFESES OBJECT-TYPE
        SYNTAX Integer32 
        MAX-ACCESS read-only
        STATUS current
        DESCRIPTION
            "This object indicates the number of severe remote errored seconds on the HP."
        ::= { hwSDHHpPerfCurrentEntry 10 }


    hwSDHHpPerfCurrentFEUAS OBJECT-TYPE
        SYNTAX Integer32 
        MAX-ACCESS read-only
        STATUS current
        DESCRIPTION
            "This object indicates the number of remote unavailable seconds on the HP."
        ::= { hwSDHHpPerfCurrentEntry 11 }


    hwSDHLpPerfCurrentTable OBJECT-TYPE
        SYNTAX  SEQUENCE OF HwSDHLpPerfCurrentEntry
        MAX-ACCESS not-accessible
        STATUS current
        DESCRIPTION
            "This table describes the access and configuration of physical attributes of lower order paths (LPs)."
        ::= { hwPhysicalPort 4 }


    hwSDHLpPerfCurrentEntry OBJECT-TYPE
        SYNTAX HwSDHLpPerfCurrentEntry 
        MAX-ACCESS not-accessible
        STATUS current
        DESCRIPTION
            "Indicates the performance stat of the Low order Path."
        INDEX { hwSDHLpPerfCurrentIfIndex,hwSDHLpPerfCurrentHpIndex,hwSDHLpPerfCurrentLpIndex,hwSDHLpPerfCurrentDataIndex }
        ::= { hwSDHLpPerfCurrentTable 1 }


    HwSDHLpPerfCurrentEntry ::= SEQUENCE {
        hwSDHLpPerfCurrentIfIndex 
            InterfaceIndex,
        hwSDHLpPerfCurrentHpIndex 
            Integer32,
        hwSDHLpPerfCurrentLpIndex 
            Integer32,
        hwSDHLpPerfCurrentDataIndex 
            Integer32,
        hwSDHLpPerfCurrentBBE 
            Integer32,
        hwSDHLpPerfCurrentES 
            Integer32,
        hwSDHLpPerfCurrentSES 
            Integer32,
        hwSDHLpPerfCurrentUAS 
            Integer32,
        hwSDHLpPerfCurrentFEBBE 
            Integer32,
        hwSDHLpPerfCurrentFEES 
            Integer32,
        hwSDHLpPerfCurrentFESES 
            Integer32,
        hwSDHLpPerfCurrentFEUAS 
            Integer32
        }


    hwSDHLpPerfCurrentIfIndex OBJECT-TYPE
        SYNTAX InterfaceIndex 
        MAX-ACCESS accessible-for-notify
        STATUS current
        DESCRIPTION
            "This object indicates the interface index."
        ::= { hwSDHLpPerfCurrentEntry 1 }


    hwSDHLpPerfCurrentHpIndex OBJECT-TYPE
        SYNTAX Integer32 
        MAX-ACCESS not-accessible
        STATUS current
        DESCRIPTION
            "This object indicates the HP index."
        ::= { hwSDHLpPerfCurrentEntry 2 }


    hwSDHLpPerfCurrentLpIndex OBJECT-TYPE
        SYNTAX Integer32 
        MAX-ACCESS not-accessible
        STATUS current
        DESCRIPTION
            "This object indicates the lower order path (LP) index."
        ::= { hwSDHLpPerfCurrentEntry 3 }


    hwSDHLpPerfCurrentDataIndex OBJECT-TYPE
        SYNTAX Integer32 (0..1)
        MAX-ACCESS not-accessible
        STATUS current
        DESCRIPTION
            "This object indicates the data index."
        ::= { hwSDHLpPerfCurrentEntry 4 }


    hwSDHLpPerfCurrentBBE OBJECT-TYPE
        SYNTAX Integer32 
        MAX-ACCESS read-only
        STATUS current
        DESCRIPTION
            "This object indicates the background errored block of the lower order path (LP)."
        ::= { hwSDHLpPerfCurrentEntry 5 }


    hwSDHLpPerfCurrentES OBJECT-TYPE
        SYNTAX Integer32 
        MAX-ACCESS read-only
        STATUS current
        DESCRIPTION
            "This object indicates the number of errored seconds on the lower order path (LP)."
        ::= { hwSDHLpPerfCurrentEntry 6 }


    hwSDHLpPerfCurrentSES OBJECT-TYPE
        SYNTAX Integer32 
        MAX-ACCESS read-only
        STATUS current
        DESCRIPTION
            "This object indicates the number of severe errored seconds on the lower order path (LP)."
        ::= { hwSDHLpPerfCurrentEntry 7 }


    hwSDHLpPerfCurrentUAS OBJECT-TYPE
        SYNTAX Integer32 
        MAX-ACCESS read-only
        STATUS current
        DESCRIPTION
            "This object indicates the number of unavailable seconds on the lower order path (LP)."
        ::= { hwSDHLpPerfCurrentEntry 8 }


    hwSDHLpPerfCurrentFEBBE OBJECT-TYPE
        SYNTAX Integer32 
        MAX-ACCESS read-only
        STATUS current
        DESCRIPTION
            "This object indicates the the remote background errored block of the lower order path (LP)."
        ::= { hwSDHLpPerfCurrentEntry 9 }


    hwSDHLpPerfCurrentFEES OBJECT-TYPE
        SYNTAX Integer32 
        MAX-ACCESS read-only
        STATUS current
        DESCRIPTION
            "This object indicates the number of remote errored seconds on the lower order path (LP)."
        ::= { hwSDHLpPerfCurrentEntry 10 }


    hwSDHLpPerfCurrentFESES OBJECT-TYPE
        SYNTAX Integer32 
        MAX-ACCESS read-only
        STATUS current
        DESCRIPTION
            "This object indicates the number of remote errored seconds on the lower order path (LP)."
        ::= { hwSDHLpPerfCurrentEntry 11 }


    hwSDHLpPerfCurrentFEUAS OBJECT-TYPE
        SYNTAX Integer32 
        MAX-ACCESS read-only
        STATUS current
        DESCRIPTION
            "This object indicates the number of unavailable seconds on the lower order path (LP)."
        ::= { hwSDHLpPerfCurrentEntry 12 }


    hwPDHPerfCurrentTable OBJECT-TYPE
        SYNTAX  SEQUENCE OF HwPDHPerfCurrentEntry
        MAX-ACCESS not-accessible
        STATUS current
        DESCRIPTION
            "This table describes functions of physical interfaces."
        ::= { hwPhysicalPort 5 }


    hwPDHPerfCurrentEntry OBJECT-TYPE
        SYNTAX HwPDHPerfCurrentEntry 
        MAX-ACCESS not-accessible
        STATUS current
        DESCRIPTION
            "Indicates the performance stat of the E1 line side."
        INDEX { hwPDHPerfCurrentIfIndex,hwPDHPerfCurrentDataIndex }
        ::= { hwPDHPerfCurrentTable 1 }


    HwPDHPerfCurrentEntry ::= SEQUENCE {
        hwPDHPerfCurrentIfIndex 
            InterfaceIndex,
        hwPDHPerfCurrentDataIndex 
            Integer32,
        hwPDHPerfCurrentBBE 
            Integer32,
        hwPDHPerfCurrentES 
            Integer32,
        hwPDHPerfCurrentSES 
            Integer32,
        hwPDHPerfCurrentUAS 
            Integer32,
        hwPDHPerfCurrentLCV 
            Integer32
        }


    hwPDHPerfCurrentIfIndex OBJECT-TYPE
        SYNTAX InterfaceIndex 
        MAX-ACCESS not-accessible
        STATUS current
        DESCRIPTION
            "This object indicates the interface index."
        ::= { hwPDHPerfCurrentEntry 1 }


    hwPDHPerfCurrentDataIndex OBJECT-TYPE
        SYNTAX Integer32 (0..1)
        MAX-ACCESS not-accessible
        STATUS current
        DESCRIPTION
            "This object indicates the data index."
        ::= { hwPDHPerfCurrentEntry 2 }


    hwPDHPerfCurrentBBE OBJECT-TYPE
        SYNTAX Integer32 
        MAX-ACCESS read-only
        STATUS current
        DESCRIPTION
            "This object indicates the background errored block of the higher order path (HP)."
        ::= { hwPDHPerfCurrentEntry 3 }


    hwPDHPerfCurrentES OBJECT-TYPE
        SYNTAX Integer32 
        MAX-ACCESS read-only
        STATUS current
        DESCRIPTION
            "This object indicates the number of errored seconds on the E1 line code."
        ::= { hwPDHPerfCurrentEntry 4 }


    hwPDHPerfCurrentSES OBJECT-TYPE
        SYNTAX Integer32 
        MAX-ACCESS read-only
        STATUS current
        DESCRIPTION
            "This object indicates the number of severe errored seconds on the E1 line code."
        ::= { hwPDHPerfCurrentEntry 5 }


    hwPDHPerfCurrentUAS OBJECT-TYPE
        SYNTAX Integer32 
        MAX-ACCESS read-only
        STATUS current
        DESCRIPTION
            "This object indicates the number of seconds for the loss of signals on the E1 line code."
        ::= { hwPDHPerfCurrentEntry 6 }


    hwPDHPerfCurrentLCV OBJECT-TYPE
        SYNTAX Integer32 
        MAX-ACCESS read-only
        STATUS current
        DESCRIPTION
            "This object indicates the number of errors on the E1 line code."
        ::= { hwPDHPerfCurrentEntry 7 }


    hwEthPortStatTable OBJECT-TYPE
        SYNTAX  SEQUENCE OF HwEthPortStatEntry
        MAX-ACCESS not-accessible
        STATUS current
        DESCRIPTION
            "This table describes the output of error packets and packet length configuration."
        ::= { hwPhysicalPort 6 }


    hwEthPortStatEntry OBJECT-TYPE
        SYNTAX HwEthPortStatEntry 
        MAX-ACCESS not-accessible
        STATUS current
        DESCRIPTION
            "Indicates the stat of the ethernet interface."
        INDEX { hwEthPortStatIfIndex }
        ::= { hwEthPortStatTable 1 }


    HwEthPortStatEntry ::= SEQUENCE {
        hwEthPortStatIfIndex 
            InterfaceIndex,
        hwEthPortStatBadBytes 
            Counter64,
        hwEthPortStatOutPut64Bytes 
            Counter64,
        hwEthPortStatOutPut65to127Bytes 
            Counter64,
        hwEthPortStatOutPut128to255Bytes 
            Counter64,
        hwEthPortStatOutPut256to511Bytes 
            Counter64,
        hwEthPortStatOutPut512to1023Bytes 
            Counter64,
        hwEthPortStatOutPut1024to1518Bytes 
            Counter64,
        hwEthPortStatOutPut1519toMaxBytes 
            Counter64
        }


    hwEthPortStatIfIndex OBJECT-TYPE
        SYNTAX InterfaceIndex 
        MAX-ACCESS not-accessible
        STATUS current
        DESCRIPTION
            "This object indicates the interface index."
        ::= { hwEthPortStatEntry 1 }


    hwEthPortStatBadBytes OBJECT-TYPE
        SYNTAX Counter64 
        MAX-ACCESS read-only
        STATUS current
        DESCRIPTION
            "This object indicates the statistics about the Badtypes errors."
        ::= { hwEthPortStatEntry 2 }


    hwEthPortStatOutPut64Bytes OBJECT-TYPE
        SYNTAX Counter64 
        MAX-ACCESS read-only
        STATUS current
        DESCRIPTION
            "This object indicates the number of output data packets each with a length less than or equal to 64 bytes."
        ::= { hwEthPortStatEntry 3 }


    hwEthPortStatOutPut65to127Bytes OBJECT-TYPE
        SYNTAX Counter64 
        MAX-ACCESS read-only
        STATUS current
        DESCRIPTION
            "This object indicates the number of output data packets each with a length ranging from 65 bytes to 127 bytes."
        ::= { hwEthPortStatEntry 4 }


    hwEthPortStatOutPut128to255Bytes OBJECT-TYPE
        SYNTAX Counter64 
        MAX-ACCESS read-only
        STATUS current
        DESCRIPTION
            "This object indicates the number of output data packets each with a length ranging from 128 bytes to 255 bytes."
        ::= { hwEthPortStatEntry 5 }


    hwEthPortStatOutPut256to511Bytes OBJECT-TYPE
        SYNTAX Counter64 
        MAX-ACCESS read-only
        STATUS current
        DESCRIPTION
            "This object indicates the number of output data packets each with a length ranging from 256 bytes to 511 bytes."
        ::= { hwEthPortStatEntry 6 }


    hwEthPortStatOutPut512to1023Bytes OBJECT-TYPE
        SYNTAX Counter64 
        MAX-ACCESS read-only
        STATUS current
        DESCRIPTION
            "This object indicates the number of output data packets each with a length ranging from 512 bytes to 1023 bytes."
        ::= { hwEthPortStatEntry 7 }


    hwEthPortStatOutPut1024to1518Bytes OBJECT-TYPE
        SYNTAX Counter64 
        MAX-ACCESS read-only
        STATUS current
        DESCRIPTION
            "This object indicates the number of output data packets each with a length ranging from 1024 bytes to 1518 bytes."
        ::= { hwEthPortStatEntry 8 }


    hwEthPortStatOutPut1519toMaxBytes OBJECT-TYPE
        SYNTAX Counter64 
        MAX-ACCESS read-only
        STATUS current
        DESCRIPTION
            "This object indicates the number of sent data packets each with a length greater than or equal to 1519 bytes."
        ::= { hwEthPortStatEntry 9 }


    hwPhysicalPortGlobleCfg OBJECT IDENTIFIER ::= { hwPhysicalPort 7 }

    hwLoopBackAutoClearEnable OBJECT-TYPE
        SYNTAX INTEGER {enable(1),disable(2)}
        MAX-ACCESS read-write
        STATUS current
        DESCRIPTION
            "set loopback autoclear status enable(1) disable(2)."
        DEFVAL { 2 }
        ::= { hwPhysicalPortGlobleCfg 1 }


    hwLoopBackAutoClearPeriod OBJECT-TYPE
        SYNTAX Integer32 (1..2880)
        UNITS "minute"
        MAX-ACCESS read-write
        STATUS current
        DESCRIPTION
            "set loopback autoclear period, unit minute,value range<1-2880> default<5 minute>."
        DEFVAL { 5 }
        ::= { hwPhysicalPortGlobleCfg 2 }


    hwPortAlarmInverseEnable OBJECT-TYPE
        SYNTAX INTEGER {enable(1),disable(2)}
        MAX-ACCESS read-write
        STATUS current
        DESCRIPTION
            "Config globle alarm inverse enable."
        ::= { hwPhysicalPortGlobleCfg 3 }

    hwEthOamPortLinkTable OBJECT-TYPE
        SYNTAX  SEQUENCE OF HwEthOamPortLinkEntry
        MAX-ACCESS not-accessible
        STATUS current
        DESCRIPTION
            "Set the physical port close enable(1) disable(2) by EthOam."
        ::= { hwPhysicalPort 8 }

    hwEthOamPortLinkEntry OBJECT-TYPE
        SYNTAX HwEthOamPortLinkEntry 
        MAX-ACCESS not-accessible
        STATUS current
        DESCRIPTION
            "Set the physical port close enable(1) disable(2) by EthOam."
        INDEX { hwPhysicalPortIfIndex }
        ::= { hwEthOamPortLinkTable 1 }

    HwEthOamPortLinkEntry ::= SEQUENCE {
        hwMepId 
            Unsigned32,
        hwUniName
            OCTET STRING
        }

    hwMepId OBJECT-TYPE
        SYNTAX Unsigned32 
        MAX-ACCESS read-only
        STATUS current
        DESCRIPTION
            "the ID of the MEP."
        ::= { hwEthOamPortLinkEntry 1 } 

    hwUniName OBJECT-TYPE
        SYNTAX OCTET STRING 
        MAX-ACCESS read-only
        STATUS current
        DESCRIPTION
            "the name of Uni interface that configed EthOam."
        ::= { hwEthOamPortLinkEntry 2 }

    hwDslGroup OBJECT IDENTIFIER ::= { hwPortMIBObjects 9 }

    hwDslGroupTable OBJECT-TYPE
        SYNTAX  SEQUENCE OF HwDslGroupEntry
        MAX-ACCESS not-accessible
        STATUS current
        DESCRIPTION
            "Indicates the attributes of the dsl group."
        ::= { hwDslGroup 1 }


    hwDslGroupEntry OBJECT-TYPE
        SYNTAX HwDslGroupEntry 
        MAX-ACCESS not-accessible
        STATUS current
        DESCRIPTION
            "An entry in the dsl group table."
        INDEX { hwDslGroupIfIndex }
        ::= { hwDslGroupTable 1 }


    HwDslGroupEntry ::= SEQUENCE {
        hwDslGroupIfIndex 
            InterfaceIndex,
        hwDslGroupWorkMode 
            INTEGER,
        hwDslGroupBisState 
            INTEGER,
        hwDslGroupEncapeMode 
            INTEGER,
        hwDslGroupEnable 
            INTEGER,
        hwDslGroupRowStatus 
            RowStatus
        }


    hwDslGroupIfIndex OBJECT-TYPE
        SYNTAX InterfaceIndex 
        MAX-ACCESS read-only
        STATUS current
        DESCRIPTION
            "Interface index(es) of dsl group present on the device."
        ::= { hwDslGroupEntry 1 }


    hwDslGroupWorkMode OBJECT-TYPE
        SYNTAX INTEGER {atm(1),efm(2)}
        MAX-ACCESS read-write
        STATUS current
        DESCRIPTION
            "The dsl group of SHD4 card can work in efm or atm mode. Default is efm.
                "
        ::= { hwDslGroupEntry 2 }


    hwDslGroupBisState OBJECT-TYPE
        SYNTAX INTEGER {disable(1),enable(2),notSupport(3)}
        MAX-ACCESS read-write
        STATUS current
        DESCRIPTION
            "Bis can be enabled or disabled in ATM mode of SHD4 card."
        ::= { hwDslGroupEntry 3 }


    hwDslGroupEncapeMode OBJECT-TYPE
        SYNTAX INTEGER {eoaLlc(1),eoaVcmux(2),notSupport(3)}
        MAX-ACCESS read-write
        STATUS current
        DESCRIPTION
            "The dsl group of AVD8 card can work in ETHoA-LLC mode or ETHoA-VCMUX mode. Default is ETHoA-LLC."
        ::= { hwDslGroupEntry 4 }


    hwDslGroupEnable OBJECT-TYPE
        SYNTAX INTEGER {disable(1),enable(2),notSupport(3)}
        MAX-ACCESS read-write
        STATUS current
        DESCRIPTION
            "Trigger the operation of binding dsl link(s) to the dsl group."
        ::= { hwDslGroupEntry 5 }


    hwDslGroupRowStatus OBJECT-TYPE
        SYNTAX RowStatus 
        MAX-ACCESS read-create
        STATUS current
        DESCRIPTION
            "An object that allows entries in this table to
                be created, modified and deleted using the RowStatus
                convention.
                A SET operation to any other attribute in this row, when
                this object is set to 'active' (1), MUST be rejected with
                an SNMP error (e.g., inconsistentValue).
                In order to perform a SET operation to any other attribute
                in this table the manager MUST set this object to
                notInService (2).  After setting the object back to
                'active' the implementation MAY tear down all the sessions
                that belong to this partition and recreate them, depending
                on what session attributes have been modified."
        ::= { hwDslGroupEntry 60 }


    hwDslGroupBoundVeTable OBJECT-TYPE
        SYNTAX  SEQUENCE OF HwDslGroupBoundVeEntry
        MAX-ACCESS not-accessible
        STATUS current
        DESCRIPTION
            "Indicates the attributes of the dsl group bound virtual-ethernet."
        ::= { hwDslGroup 2 }


    hwDslGroupBoundVeEntry OBJECT-TYPE
        SYNTAX HwDslGroupBoundVeEntry 
        MAX-ACCESS not-accessible
        STATUS current
        DESCRIPTION
            "An entry in the dsl group bound vitrual-ethernet table."
        INDEX { hwDslGroupIfIndexOfBound,hwDslGroupPvcId }
        ::= { hwDslGroupBoundVeTable 1 }


    HwDslGroupBoundVeEntry ::= SEQUENCE {
        hwDslGroupIfIndexOfBound 
            InterfaceIndex,
        hwVirtualEthernetIfIndex 
            InterfaceIndex,
        hwDslGroupVpi 
            Integer32,
        hwDslGroupVci 
            Integer32,
        hwDslGroupPvcId 
            Integer32,
        hwBoundVeRowStatus 
            RowStatus
        }


    hwDslGroupIfIndexOfBound OBJECT-TYPE
        SYNTAX InterfaceIndex 
        MAX-ACCESS read-only
        STATUS current
        DESCRIPTION
            "Interface index(es) of dsl group present on the device."
        ::= { hwDslGroupBoundVeEntry 1 }


    hwVirtualEthernetIfIndex OBJECT-TYPE
        SYNTAX InterfaceIndex 
        MAX-ACCESS read-only
        STATUS current
        DESCRIPTION
            "The first virtual ethernet interface which the dsl group is bound to."
        ::= { hwDslGroupBoundVeEntry 2 }


    hwDslGroupVpi OBJECT-TYPE
        SYNTAX Integer32 (0..4095)
        MAX-ACCESS read-write
        STATUS current
        DESCRIPTION
            "VPI value of the 1st PVC pair."
        ::= { hwDslGroupBoundVeEntry 3 }


    hwDslGroupVci OBJECT-TYPE
        SYNTAX Integer32 (0..65535)
        MAX-ACCESS read-write
        STATUS current
        DESCRIPTION
            "VCI value of the 1st PVC pair."
        ::= { hwDslGroupBoundVeEntry 4 }


    hwDslGroupPvcId OBJECT-TYPE
        SYNTAX Integer32 (1..2)
        MAX-ACCESS read-only
        STATUS current
        DESCRIPTION
            "Identifier for VPI/VCI Pair."
        ::= { hwDslGroupBoundVeEntry 5 }


    hwBoundVeRowStatus OBJECT-TYPE
        SYNTAX RowStatus 
        MAX-ACCESS read-create
        STATUS obsolete
        DESCRIPTION
            "An object that allows entries in this table to
                be created, modified and deleted using the RowStatus
                convention.
                A SET operation to any other attribute in this row, when
                this object is set to 'active' (1), MUST be rejected with
                an SNMP error (e.g., inconsistentValue).
                In order to perform a SET operation to any other attribute
                in this table the manager MUST set this object to
                notInService (2).  After setting the object back to
                'active' the implementation MAY tear down all the sessions
                that belong to this partition and recreate them, depending
                on what session attributes have been modified."
        ::= { hwDslGroupBoundVeEntry 50 }


    hwDslGroupBindVeTable OBJECT-TYPE
        SYNTAX  SEQUENCE OF HwDslGroupBindVeEntry
        MAX-ACCESS not-accessible
        STATUS current
        DESCRIPTION
            "Indicates the relation of the dsl group binding virtual-ethernet."
        ::= { hwDslGroup 3 }


    hwDslGroupBindVeEntry OBJECT-TYPE
        SYNTAX HwDslGroupBindVeEntry 
        MAX-ACCESS not-accessible
        STATUS current
        DESCRIPTION
            "An entry in the dsl group binding vitrual-ethernet table."
        INDEX { hwDslGroupInterfaceIndex,hwVirtualEthernetInterfaceIndex }
        ::= { hwDslGroupBindVeTable 1 }


    HwDslGroupBindVeEntry ::= SEQUENCE {
        hwDslGroupInterfaceIndex 
            InterfaceIndex,
        hwVirtualEthernetInterfaceIndex 
            InterfaceIndex,
        hwBindVeRowStatus 
            RowStatus
        }


    hwDslGroupInterfaceIndex OBJECT-TYPE
        SYNTAX InterfaceIndex 
        MAX-ACCESS read-only
        STATUS current
        DESCRIPTION
            "Interface index(es) of the dsl group present on the device."
        ::= { hwDslGroupBindVeEntry 1 }


    hwVirtualEthernetInterfaceIndex OBJECT-TYPE
        SYNTAX InterfaceIndex 
        MAX-ACCESS read-only
        STATUS current
        DESCRIPTION
            "The virtual ethernet interface index which the dsl group is bound to."
        ::= { hwDslGroupBindVeEntry 2 }


    hwBindVeRowStatus OBJECT-TYPE
        SYNTAX RowStatus 
        MAX-ACCESS read-create
        STATUS current
        DESCRIPTION
            "An object that allows entries in this table to
                be created, modified and deleted using the RowStatus
                convention.
                A SET operation to any other attribute in this row, when
                this object is set to 'active' (1), MUST be rejected with
                an SNMP error (e.g., inconsistentValue).
                In order to perform a SET operation to any other attribute
                in this table the manager MUST set this object to
                notInService (2).  After setting the object back to
                'active' the implementation MAY tear down all the sessions
                that belong to this partition and recreate them, depending
                on what session attributes have been modified."
        ::= { hwDslGroupBindVeEntry 50 }


    hwDslGroupIma OBJECT IDENTIFIER ::= { hwPortMIBObjects 10 }

    hwDslGroupImaTable OBJECT-TYPE
        SYNTAX  SEQUENCE OF HwDslGroupImaEntry
        MAX-ACCESS not-accessible
        STATUS current
        DESCRIPTION
            "Indicates the attributes of the dsl ima group."
        ::= { hwDslGroupIma 1 }


    hwDslGroupImaEntry OBJECT-TYPE
        SYNTAX HwDslGroupImaEntry 
        MAX-ACCESS not-accessible
        STATUS current
        DESCRIPTION
            "An entry of the dsl ima group table."
        INDEX { hwDslGroupImaIfIndex }
        ::= { hwDslGroupImaTable 1 }


    HwDslGroupImaEntry ::= SEQUENCE {
        hwDslGroupImaIfIndex 
            InterfaceIndex,
        hwDslGroupImaVersion 
            INTEGER,
        hwDslGroupImaFrameLen 
            ImaFrameLength,
        hwDslGroupImaReset 
            INTEGER,
        hwDslGroupImaTxMinLinkNum 
            Integer32,
        hwDslGroupImaRxMinLinkNum 
            Integer32,
        hwDslGroupImaNeState 
            ImaGroupState,
        hwDslGroupImaFeState 
            ImaGroupState,
        hwDslGroupImaTxCellRate 
            Integer32,
        hwDslGroupImaRxCellRate 
            Integer32,
        hwDslGroupImaTxActLinkNum 
            Integer32,
        hwDslGroupImaRxActLinkNum 
            Integer32,
        hwDslGroupImaIfName 
            OCTET STRING
        }


    hwDslGroupImaIfIndex OBJECT-TYPE
        SYNTAX InterfaceIndex 
        MAX-ACCESS read-only
        STATUS current
        DESCRIPTION
            "Interface index(es) of dsl group present on the device."
        ::= { hwDslGroupImaEntry 1 }


    hwDslGroupImaVersion OBJECT-TYPE
        SYNTAX INTEGER {v0(1),v1(2)}
        MAX-ACCESS read-write
        STATUS current
        DESCRIPTION
            "Version of the ima group of SHD4I card.
                v0: ima protocol version 1.0;
                v1: ima protocol version 1.1. "
        ::= { hwDslGroupImaEntry 2 }


    hwDslGroupImaFrameLen OBJECT-TYPE
        SYNTAX ImaFrameLength 
        MAX-ACCESS read-write
        STATUS current
        DESCRIPTION
            "Frame length of the ima group of SHD4I card. If ima protocol version is 1.0, the frame length is only 128."
        ::= { hwDslGroupImaEntry 3 }


    hwDslGroupImaReset OBJECT-TYPE
        SYNTAX INTEGER {disable(1),enable(2)}
        MAX-ACCESS read-write
        STATUS current
        DESCRIPTION
            "ima group reset for SHD4I card."
        ::= { hwDslGroupImaEntry 4 }


    hwDslGroupImaTxMinLinkNum OBJECT-TYPE
        SYNTAX Integer32 (1..4)
        MAX-ACCESS read-write
        STATUS current
        DESCRIPTION
            "Minimum active links number by TX direction."
        ::= { hwDslGroupImaEntry 5 }


    hwDslGroupImaRxMinLinkNum OBJECT-TYPE
        SYNTAX Integer32 (1..4)
        MAX-ACCESS read-write
        STATUS current
        DESCRIPTION
            "Minimum active links number by RX direction.
                "
        ::= { hwDslGroupImaEntry 6 }


    hwDslGroupImaNeState OBJECT-TYPE
        SYNTAX ImaGroupState 
        MAX-ACCESS read-only
        STATUS current
        DESCRIPTION
            "The current state of the near-end ima group."
        ::= { hwDslGroupImaEntry 7 }


    hwDslGroupImaFeState OBJECT-TYPE
        SYNTAX ImaGroupState 
        MAX-ACCESS read-only
        STATUS current
        DESCRIPTION
            "The current state of the far-end ima group."
        ::= { hwDslGroupImaEntry 8 }


    hwDslGroupImaTxCellRate OBJECT-TYPE
        SYNTAX Integer32 
        MAX-ACCESS read-only
        STATUS current
        DESCRIPTION
            "The current cell rate of ima group by TX direction."
        ::= { hwDslGroupImaEntry 9 }


    hwDslGroupImaRxCellRate OBJECT-TYPE
        SYNTAX Integer32 
        MAX-ACCESS read-only
        STATUS current
        DESCRIPTION
            "The current cell rate of ima group by RX direction."
        ::= { hwDslGroupImaEntry 10 }


    hwDslGroupImaTxActLinkNum OBJECT-TYPE
        SYNTAX Integer32 (0..4)
        MAX-ACCESS read-only
        STATUS current
        DESCRIPTION
            "Number of active links by TX direction."
        ::= { hwDslGroupImaEntry 11 }


    hwDslGroupImaRxActLinkNum OBJECT-TYPE
        SYNTAX Integer32 (0..4)
        MAX-ACCESS read-only
        STATUS current
        DESCRIPTION
            "Number of active links by RX direction."
        ::= { hwDslGroupImaEntry 12 }


    hwDslGroupImaIfName OBJECT-TYPE
        SYNTAX OCTET STRING 
        MAX-ACCESS read-only
        STATUS current
        DESCRIPTION
            "The interface name of ima group."
        ::= { hwDslGroupImaEntry 13 }


    hwDslLink OBJECT IDENTIFIER ::= { hwPortMIBObjects 11 }

    hwDslLinkTable OBJECT-TYPE
        SYNTAX  SEQUENCE OF HwDslLinkEntry
        MAX-ACCESS not-accessible
        STATUS current
        DESCRIPTION
            "Indicates the dsl link bound relation."
        ::= { hwDslLink 1 }


    hwDslLinkEntry OBJECT-TYPE
        SYNTAX HwDslLinkEntry 
        MAX-ACCESS not-accessible
        STATUS current
        DESCRIPTION
            "An entry of the dsl link bound relation."
        INDEX { hwBoundDslGroupIfIndex,hwDslLinkIfIndex }
        ::= { hwDslLinkTable 1 }


    HwDslLinkEntry ::= SEQUENCE {
        hwBoundDslGroupIfIndex 
            InterfaceIndex,
        hwDslLinkIfIndex 
            InterfaceIndex,
        hwDslLinkIfName 
            OCTET STRING,
        hwBoundDslGroupIfName 
            OCTET STRING,
        hwDslLinkBoundRowStatus 
            RowStatus
        }


    hwBoundDslGroupIfIndex OBJECT-TYPE
        SYNTAX InterfaceIndex 
        MAX-ACCESS read-only
        STATUS current
        DESCRIPTION
            "Interface index of dsl group which the dsl link bound to."
        ::= { hwDslLinkEntry 1 }


    hwDslLinkIfIndex OBJECT-TYPE
        SYNTAX InterfaceIndex 
        MAX-ACCESS read-write
        STATUS current
        DESCRIPTION
            "Interface index of the dsl link device."
        ::= { hwDslLinkEntry 2 }


    hwDslLinkIfName OBJECT-TYPE
        SYNTAX OCTET STRING 
        MAX-ACCESS read-only
        STATUS current
        DESCRIPTION
            "The interface name of the dsl link."
        ::= { hwDslLinkEntry 4 }


    hwBoundDslGroupIfName OBJECT-TYPE
        SYNTAX OCTET STRING 
        MAX-ACCESS read-only
        STATUS current
        DESCRIPTION
            "Interface index of dsl group which the dsl link bound to."
        ::= { hwDslLinkEntry 5 }


    hwDslLinkBoundRowStatus OBJECT-TYPE
        SYNTAX RowStatus 
        MAX-ACCESS read-create
        STATUS current
        DESCRIPTION
            "An object that allows entries in this table to
        be created, modified and deleted using the RowStatus
        convention.
        A SET operation to any other attribute in this row, when
        this object is set to 'active' (1), MUST be rejected with
        an SNMP error (e.g., inconsistentValue).
        In order to perform a SET operation to any other attribute
        in this table the manager MUST set this object to
        notInService (2).  After setting the object back to
        'active' the implementation MAY tear down all the sessions
        that belong to this partition and recreate them, depending
        on what session attributes have been modified."
        ::= { hwDslLinkEntry 50 }


    hwPWAlarm OBJECT IDENTIFIER ::= { hwPortMIBObjects 12 }

    hwPWAlarmTable OBJECT-TYPE
        SYNTAX  SEQUENCE OF HwPWAlarmEntry
        MAX-ACCESS not-accessible
        STATUS current
        DESCRIPTION
            "Indicates the attributes of the PW alarm."
        ::= { hwPWAlarm 1 }


    hwPWAlarmEntry OBJECT-TYPE
        SYNTAX HwPWAlarmEntry 
        MAX-ACCESS not-accessible
        STATUS current
        DESCRIPTION
            "An entry of the PW alarm relation."
        INDEX { hwPWAlarmIfIndex }
        ::= { hwPWAlarmTable 1 }


    HwPWAlarmEntry ::= SEQUENCE {
        hwPWAlarmIfIndex 
            InterfaceIndex,
        hwPWCesVcID 
            Integer32,
        hwPWCesVcType 
            Integer32,
        hwPeerIpAddr 
            IpAddress,
        hwAlarmStatus 
            Integer32,
        hwPWAlarmRMLEnableStatus 
            EnabledStatus,
        hwLosAlarmTriggerThreshold 
            Integer32,
        hwLosAlarmResumeThreshold 
            Integer32,
        hwPWPortName 
            OCTET STRING,
        hwLosPktExcTriggerThreshold 
            Integer32,
        hwLosPktExcResumeThreshold 
            Integer32,
        hwMisorderPktExcTriggerThreshold 
            Integer32,
        hwMisorderPktExcResumeThreshold 
            Integer32,
        hwStrayPktExcTriggerThreshold 
            Integer32,
        hwStrayPktExcResumeThreshold 
            Integer32,
        hwMalPktExcTriggerThreshold 
            Integer32,
        hwMalPktExcResumeThreshold 
            Integer32,
        hwJtrUdrExcTriggerThreshold 
            Integer32,
        hwJtrUdrExcResumeThreshold 
            Integer32,
        hwJtrOvrExcTriggerThreshold 
            Integer32,
        hwJtrOvrExcResumeThreshold 
            Integer32
        }


    hwPWAlarmIfIndex OBJECT-TYPE
        SYNTAX InterfaceIndex 
        MAX-ACCESS not-accessible
        STATUS current
        DESCRIPTION
            "Interface index of PW alarm group."
        ::= { hwPWAlarmEntry 1 }


    hwPWCesVcID OBJECT-TYPE
        SYNTAX Integer32 
        MAX-ACCESS read-only
        STATUS current
        DESCRIPTION
            "Vc ID of PW alarm group."
        ::= { hwPWAlarmEntry 2 }


    hwPWCesVcType OBJECT-TYPE
        SYNTAX Integer32 
        MAX-ACCESS read-only
        STATUS current
        DESCRIPTION
            "Vc Type of PW alarm group."
        ::= { hwPWAlarmEntry 3 }


    hwPeerIpAddr OBJECT-TYPE
        SYNTAX IpAddress 
        MAX-ACCESS read-only
        STATUS current
        DESCRIPTION
            "Peer IP Address of PW alarm group."
        ::= { hwPWAlarmEntry 4 }


    hwAlarmStatus OBJECT-TYPE
        SYNTAX Integer32 
        MAX-ACCESS read-only
        STATUS obsolete
        DESCRIPTION
            "Alarm status of PW alarm group."
        ::= { hwPWAlarmEntry 5 }


    hwPWAlarmRMLEnableStatus OBJECT-TYPE
        SYNTAX EnabledStatus 
        MAX-ACCESS read-write
        STATUS current
        DESCRIPTION
            "PW control word RML of PW alarm group."
        ::= { hwPWAlarmEntry 6 }


    hwLosAlarmTriggerThreshold OBJECT-TYPE
        SYNTAX Integer32 (2..65535)
        MAX-ACCESS read-write
        STATUS current
        DESCRIPTION
            "Trigger Threshold of continuous loss packets of PW alarm group."
        DEFVAL { 100 }
        ::= { hwPWAlarmEntry 7 }


    hwLosAlarmResumeThreshold OBJECT-TYPE
        SYNTAX Integer32 (32..65535)
        MAX-ACCESS read-write
        STATUS current
        DESCRIPTION
            "Resume Threshold of continuous loss packets of PW alarm group."
        DEFVAL { 5 }
        ::= { hwPWAlarmEntry 8 }


    hwPWPortName OBJECT-TYPE
        SYNTAX OCTET STRING 
        MAX-ACCESS read-only
        STATUS current
        DESCRIPTION
            "PW port name of PW alarm group."
        ::= { hwPWAlarmEntry 9 }


    hwLosPktExcTriggerThreshold OBJECT-TYPE
        SYNTAX Integer32 
        MAX-ACCESS read-write
        STATUS current
        DESCRIPTION
            "Trigger threshold of lost packets of PW alarm group."
        ::= { hwPWAlarmEntry 10 }


    hwLosPktExcResumeThreshold OBJECT-TYPE
        SYNTAX Integer32 
        MAX-ACCESS read-write
        STATUS current
        DESCRIPTION
            "Resume threshold of lost packets of PW alarm group."
        ::= { hwPWAlarmEntry 11 }


    hwMisorderPktExcTriggerThreshold OBJECT-TYPE
        SYNTAX Integer32 
        MAX-ACCESS read-write
        STATUS current
        DESCRIPTION
            "Trigger threshold of packets lost due to the out-of-order condition of PW alarm group."
        ::= { hwPWAlarmEntry 12 }


    hwMisorderPktExcResumeThreshold OBJECT-TYPE
        SYNTAX Integer32 
        MAX-ACCESS read-write
        STATUS current
        DESCRIPTION
            "Resume threshold of packets lost due to the out-of-order condition of PW alarm group."
        ::= { hwPWAlarmEntry 13 }


    hwStrayPktExcTriggerThreshold OBJECT-TYPE
        SYNTAX Integer32 
        MAX-ACCESS read-write
        STATUS current
        DESCRIPTION
            "Trigger threshold of misconnected packets of PW alarm group."
        ::= { hwPWAlarmEntry 14 }


    hwStrayPktExcResumeThreshold OBJECT-TYPE
        SYNTAX Integer32 
        MAX-ACCESS read-write
        STATUS current
        DESCRIPTION
            "Resume threshold of misconnected packets of PW alarm group."
        ::= { hwPWAlarmEntry 15 }


    hwMalPktExcTriggerThreshold OBJECT-TYPE
        SYNTAX Integer32 
        MAX-ACCESS read-write
        STATUS current
        DESCRIPTION
            "Trigger threshold of malformed packets of PW alarm group."
        ::= { hwPWAlarmEntry 16 }


    hwMalPktExcResumeThreshold OBJECT-TYPE
        SYNTAX Integer32 
        MAX-ACCESS read-write
        STATUS current
        DESCRIPTION
            "Resume threshold of malformed packets of PW alarm group."
        ::= { hwPWAlarmEntry 17 }


    hwJtrUdrExcTriggerThreshold OBJECT-TYPE
        SYNTAX Integer32 
        MAX-ACCESS read-write
        STATUS current
        DESCRIPTION
            "Trigger threshold of jitter buffer underflows of PW alarm group."
        ::= { hwPWAlarmEntry 18 }


    hwJtrUdrExcResumeThreshold OBJECT-TYPE
        SYNTAX Integer32 
        MAX-ACCESS read-write
        STATUS current
        DESCRIPTION
            "Resume threshold of jitter buffer underflows of PW alarm group."
        ::= { hwPWAlarmEntry 19 }


    hwJtrOvrExcTriggerThreshold OBJECT-TYPE
        SYNTAX Integer32 
        MAX-ACCESS read-write
        STATUS current
        DESCRIPTION
            "Trigger threshold of jitter buffer overflows of PW alarm group."
        ::= { hwPWAlarmEntry 20 }


    hwJtrOvrExcResumeThreshold OBJECT-TYPE
        SYNTAX Integer32 
        MAX-ACCESS read-write
        STATUS current
        DESCRIPTION
            "Resume threshold of jitter buffer overflows of PW alarm group."
        ::= { hwPWAlarmEntry 21 }


    hwAtmPWAlarmTable OBJECT-TYPE
        SYNTAX  SEQUENCE OF HwAtmPWAlarmEntry
        MAX-ACCESS not-accessible
        STATUS current
        DESCRIPTION
            "Indicates the attributes of the ATM PW alarm."
        ::= { hwPWAlarm 2 }


    hwAtmPWAlarmEntry OBJECT-TYPE
        SYNTAX HwAtmPWAlarmEntry 
        MAX-ACCESS not-accessible
        STATUS current
        DESCRIPTION
            "An entry of the ATM PW alarm relation."
        INDEX { hwAtmPWAlarmIfIndex }
        ::= { hwAtmPWAlarmTable 1 }


    HwAtmPWAlarmEntry ::= SEQUENCE {
        hwAtmPWAlarmIfIndex 
            InterfaceIndex,
        hwAtmVcID 
            Integer32,
        hwAtmVcType 
            Integer32,
        hwAtmPeerIpAddr 
            IpAddress,
        hwAtmPWPortName 
            OCTET STRING,
        hwAtmLosPktExcTriggerThreshold 
            Integer32,
        hwAtmLosPktExcResumeThreshold 
            Integer32,
        hwAtmMisorderPktExcTriggerThreshold 
            Integer32,
        hwAtmMisorderPktExcResumeThreshold 
            Integer32,
        hwAtmUnknownCellExcTriggerThreshold 
            Integer32,
        hwAtmUnknownCellExcResumeThreshold 
            Integer32
        }


    hwAtmPWAlarmIfIndex OBJECT-TYPE
        SYNTAX InterfaceIndex 
        MAX-ACCESS read-only
        STATUS current
        DESCRIPTION
            "Interface index of ATM PW alarm group."
        ::= { hwAtmPWAlarmEntry 1 }


    hwAtmVcID OBJECT-TYPE
        SYNTAX Integer32 
        MAX-ACCESS read-only
        STATUS current
        DESCRIPTION
            "Vc ID of ATM PW alarm group."
        ::= { hwAtmPWAlarmEntry 2 }


    hwAtmVcType OBJECT-TYPE
        SYNTAX Integer32 
        MAX-ACCESS read-only
        STATUS current
        DESCRIPTION
            "Vc Type of ATM PW alarm group."
        ::= { hwAtmPWAlarmEntry 3 }


    hwAtmPeerIpAddr OBJECT-TYPE
        SYNTAX IpAddress 
        MAX-ACCESS read-only
        STATUS current
        DESCRIPTION
            "Peer IP Address of ATM PW alarm group."
        ::= { hwAtmPWAlarmEntry 4 }


    hwAtmPWPortName OBJECT-TYPE
        SYNTAX OCTET STRING 
        MAX-ACCESS read-only
        STATUS current
        DESCRIPTION
            "ATM PW port name of PW alarm group."
        ::= { hwAtmPWAlarmEntry 5 }


    hwAtmLosPktExcTriggerThreshold OBJECT-TYPE
        SYNTAX Integer32 (1..1000)
        MAX-ACCESS read-write
        STATUS current
        DESCRIPTION
            "Trigger threshold of lost packets of ATM PW alarm group."
        DEFVAL { 100 }
        ::= { hwAtmPWAlarmEntry 6 }


    hwAtmLosPktExcResumeThreshold OBJECT-TYPE
        SYNTAX Integer32 (1..1000)
        MAX-ACCESS read-write
        STATUS current
        DESCRIPTION
            "Resume threshold of lost packets of ATM PW alarm group."
        DEFVAL { 1 }
        ::= { hwAtmPWAlarmEntry 7 }


    hwAtmMisorderPktExcTriggerThreshold OBJECT-TYPE
        SYNTAX Integer32 (1..1000)
        MAX-ACCESS read-write
        STATUS current
        DESCRIPTION
            "Trigger threshold of packets lost due to the out-of-order condition of ATM PW alarm group."
        DEFVAL { 100 }
        ::= { hwAtmPWAlarmEntry 8 }


    hwAtmMisorderPktExcResumeThreshold OBJECT-TYPE
        SYNTAX Integer32 (1..1000)
        MAX-ACCESS read-write
        STATUS current
        DESCRIPTION
            "Resume threshold of packets lost due to the out-of-order condition of ATM PW alarm group."
        DEFVAL { 1 }
        ::= { hwAtmPWAlarmEntry 9 }


    hwAtmUnknownCellExcTriggerThreshold OBJECT-TYPE
        SYNTAX Integer32 (1..1000)
        MAX-ACCESS read-write
        STATUS current
        DESCRIPTION
            "Trigger threshold of unknown cell of ATM PW alarm group."
        DEFVAL { 100 }
        ::= { hwAtmPWAlarmEntry 10 }


    hwAtmUnknownCellExcResumeThreshold OBJECT-TYPE
        SYNTAX Integer32 (1..1000)
        MAX-ACCESS read-write
        STATUS current
        DESCRIPTION
            "Resume threshold of unknown cell of ATM PW alarm group."
        DEFVAL { 1 }
        ::= { hwAtmPWAlarmEntry 11 }


    hwSNMPTrapEn OBJECT IDENTIFIER ::= { hwPortMIBObjects 13 }

    hwSNMPTrapEnTable OBJECT-TYPE
        SYNTAX  SEQUENCE OF HwSNMPTrapEnEntry
        MAX-ACCESS not-accessible
        STATUS current
        DESCRIPTION
            "Reserved nodes do not support this function temporarily."
        ::= { hwSNMPTrapEn 1 }


    hwSNMPTrapEnEntry OBJECT-TYPE
        SYNTAX HwSNMPTrapEnEntry 
        MAX-ACCESS not-accessible
        STATUS current
        DESCRIPTION
            "Reserved nodes do not support this function temporarily."
        INDEX { hwSNMPTrapEnIfIndex }
        ::= { hwSNMPTrapEnTable 1 }


    HwSNMPTrapEnEntry ::= SEQUENCE {
        hwSNMPTrapEnIfIndex 
            InterfaceIndex,
        hwCesPWLopsEn 
            Integer32,
        hwCesPWRemoteLosPktEn 
            Integer32,
        hwCesPWOppositeRAIEn 
            Integer32,
        hwCesPWOppositeAcfaultEn 
            Integer32,
        hwCesPWLosPktEn 
            Integer32,
        hwCesPWMisorderPktEn 
            Integer32,
        hwCesPWStrayPktEn 
            Integer32,
        hwCesPWMalPktEn 
            Integer32,
        hwCesPWJtrUnrEn 
            Integer32,
        hwCesPWJtrOvrEn 
            Integer32,
        hwCesPWAllEn 
            Integer32,
        hwPhysicalPortLosAlarmEn 
            Integer32,
        hwPhysicalPortLofAlarmEn 
            Integer32,
        hwRsOofAlarmEn 
            Integer32,
        hwRsB1ExcAlarmEn 
            Integer32,
        hwRsB1SdAlarmEn 
            Integer32,
        hwRsJ0TimAlarmEn 
            Integer32,
        hwMsRdiAlarmEn 
            Integer32,
        hwMsB2ExcAlarmEn 
            Integer32,
        hwMsAuLopAlarmEn 
            Integer32,
        hwMsAisAlarmEn 
            Integer32,
        hwMsB2SdAlarmEn 
            Integer32,
        hwHpJ1TimAlarmEn 
            Integer32,
        hwHpUneqAlarmEn 
            Integer32,
        hwHpRdiAlarmEn 
            Integer32,
        hwHpB3ExcAlarmEn 
            Integer32,
        hwHpPlmAlarmEn 
            Integer32,
        hwHpB3SdAlarmEn 
            Integer32,
        hwHpAuAisAlarmEn 
            Integer32,
        hwLpTuLopAlarmEn 
            Integer32,
        hwHpTuLomAlarmEn 
            Integer32,
        hwLpTimAlarmEn 
            Integer32,
        hwLpUneqAlarmEn 
            Integer32,
        hwLpRdiAlarmEn 
            Integer32,
        hwLpBipExcAlarmEn 
            Integer32,
        hwLpBipSdAlarmEn 
            Integer32,
        hwLpPlmAlarmEn 
            Integer32,
        hwLpTuAisAlarmEn 
            Integer32,
        hwDs1EsExcAlarmEn 
            Integer32,
        hwDs1RmfaAlarmEn 
            Integer32,
        hwDs1LmfaAlarmEn 
            Integer32,
        hwDs1AisAlarmEn 
            Integer32,
        hwDs1RdiAlarmEn 
            Integer32,
        hwRsLocAlarmEn 
            Integer32,
        hwLpRfiAlarmEn 
            Integer32,
        hwLpV5VcaisAlarmEn 
            Integer32,
        hwVc12oofAlarmEn 
            Integer32,
        hwVc12AlmE1RaiAlarmEn 
            Integer32,
        hwVc12LfaAlarmEn 
            Integer32,
        hwVc12UpE1AisAlarmEn 
            Integer32,
        hwVc12DownE1AisAlarmEn 
            Integer32,
        hwDs1DownE1AisAlarmEn 
            Integer32,
        hwMsLpsUniBiMAlarmEn 
            Integer32,
        hwMsK1K2MAlarmEn 
            Integer32,
        hwMsK2MAlarmEn 
            Integer32,
        hwVc12LmfaAlarmEn 
            Integer32,
        hwSDHAllEn 
            Integer32,
        hwLaserShutAlarmEn 
            Integer32,
        hwLaserAutoShutAlarmEn 
            Integer32,
        hwLaserAllEn 
            Integer32,
        hwLoopbackAlarmEn 
            Integer32,
        hwChannelLoopbackAlarmEn 
            Integer32,
        hwLoopbackAllEn 
            Integer32,
        hwAtmOcdAlarmEn 
            Integer32,
        hwAtmLcdAlarmEn 
            Integer32,
        hwAtmUhcsAlarmEn 
            Integer32,
        hwAtmChcsAlarmEn 
            Integer32,
        hwAtmPWLosPktEn 
            Integer32,
        hwAtmPWMisorderPktEn 
            Integer32,
        hwAtmPWUnknownCellEn 
            Integer32,
        hwAtmAllEn 
            Integer32
        }


    hwSNMPTrapEnIfIndex OBJECT-TYPE
        SYNTAX InterfaceIndex 
        MAX-ACCESS not-accessible
        STATUS current
        DESCRIPTION
            "Reserved nodes do not support this function temporarily."
        ::= { hwSNMPTrapEnEntry 1 }


    hwCesPWLopsEn OBJECT-TYPE
        SYNTAX Integer32 
        MAX-ACCESS read-write
        STATUS current
        DESCRIPTION
            "Reserved nodes do not support this function temporarily."
        ::= { hwSNMPTrapEnEntry 2 }


    hwCesPWRemoteLosPktEn OBJECT-TYPE
        SYNTAX Integer32 
        MAX-ACCESS read-write
        STATUS current
        DESCRIPTION
            "Reserved nodes do not support this function temporarily."
        ::= { hwSNMPTrapEnEntry 3 }


    hwCesPWOppositeRAIEn OBJECT-TYPE
        SYNTAX Integer32 
        MAX-ACCESS read-write
        STATUS current
        DESCRIPTION
            "Reserved nodes do not support this function temporarily."
        ::= { hwSNMPTrapEnEntry 4 }


    hwCesPWOppositeAcfaultEn OBJECT-TYPE
        SYNTAX Integer32 
        MAX-ACCESS read-write
        STATUS current
        DESCRIPTION
            "Reserved nodes do not support this function temporarily."
        ::= { hwSNMPTrapEnEntry 5 }


    hwCesPWLosPktEn OBJECT-TYPE
        SYNTAX Integer32 
        MAX-ACCESS read-write
        STATUS current
        DESCRIPTION
            "Reserved nodes do not support this function temporarily."
        ::= { hwSNMPTrapEnEntry 6 }


    hwCesPWMisorderPktEn OBJECT-TYPE
        SYNTAX Integer32 
        MAX-ACCESS read-write
        STATUS current
        DESCRIPTION
            "Reserved nodes do not support this function temporarily."
        ::= { hwSNMPTrapEnEntry 7 }


    hwCesPWStrayPktEn OBJECT-TYPE
        SYNTAX Integer32 
        MAX-ACCESS read-write
        STATUS current
        DESCRIPTION
            "Reserved nodes do not support this function temporarily."
        ::= { hwSNMPTrapEnEntry 8 }


    hwCesPWMalPktEn OBJECT-TYPE
        SYNTAX Integer32 
        MAX-ACCESS read-write
        STATUS current
        DESCRIPTION
            "Reserved nodes do not support this function temporarily."
        ::= { hwSNMPTrapEnEntry 9 }


    hwCesPWJtrUnrEn OBJECT-TYPE
        SYNTAX Integer32 
        MAX-ACCESS read-write
        STATUS current
        DESCRIPTION
            "Reserved nodes do not support this function temporarily."
        ::= { hwSNMPTrapEnEntry 10 }


    hwCesPWJtrOvrEn OBJECT-TYPE
        SYNTAX Integer32 
        MAX-ACCESS read-write
        STATUS current
        DESCRIPTION
            "Reserved nodes do not support this function temporarily."
        ::= { hwSNMPTrapEnEntry 11 }


    hwCesPWAllEn OBJECT-TYPE
        SYNTAX Integer32 
        MAX-ACCESS read-write
        STATUS current
        DESCRIPTION
            "Reserved nodes do not support this function temporarily."
        ::= { hwSNMPTrapEnEntry 12 }


    hwPhysicalPortLosAlarmEn OBJECT-TYPE
        SYNTAX Integer32 
        MAX-ACCESS read-write
        STATUS current
        DESCRIPTION
            "Reserved nodes do not support this function temporarily."
        ::= { hwSNMPTrapEnEntry 13 }


    hwPhysicalPortLofAlarmEn OBJECT-TYPE
        SYNTAX Integer32 
        MAX-ACCESS read-write
        STATUS current
        DESCRIPTION
            "Reserved nodes do not support this function temporarily."
        ::= { hwSNMPTrapEnEntry 14 }


    hwRsOofAlarmEn OBJECT-TYPE
        SYNTAX Integer32 
        MAX-ACCESS read-write
        STATUS current
        DESCRIPTION
            "Reserved nodes do not support this function temporarily."
        ::= { hwSNMPTrapEnEntry 15 }


    hwRsB1ExcAlarmEn OBJECT-TYPE
        SYNTAX Integer32 
        MAX-ACCESS read-write
        STATUS current
        DESCRIPTION
            "Reserved nodes do not support this function temporarily."
        ::= { hwSNMPTrapEnEntry 16 }


    hwRsB1SdAlarmEn OBJECT-TYPE
        SYNTAX Integer32 
        MAX-ACCESS read-write
        STATUS current
        DESCRIPTION
            "Reserved nodes do not support this function temporarily."
        ::= { hwSNMPTrapEnEntry 17 }


    hwRsJ0TimAlarmEn OBJECT-TYPE
        SYNTAX Integer32 
        MAX-ACCESS read-write
        STATUS current
        DESCRIPTION
            "Reserved nodes do not support this function temporarily."
        ::= { hwSNMPTrapEnEntry 18 }


    hwMsRdiAlarmEn OBJECT-TYPE
        SYNTAX Integer32 
        MAX-ACCESS read-write
        STATUS current
        DESCRIPTION
            "Reserved nodes do not support this function temporarily."
        ::= { hwSNMPTrapEnEntry 19 }


    hwMsB2ExcAlarmEn OBJECT-TYPE
        SYNTAX Integer32 
        MAX-ACCESS read-write
        STATUS current
        DESCRIPTION
            "Reserved nodes do not support this function temporarily."
        ::= { hwSNMPTrapEnEntry 20 }


    hwMsAuLopAlarmEn OBJECT-TYPE
        SYNTAX Integer32 
        MAX-ACCESS read-write
        STATUS current
        DESCRIPTION
            "Reserved nodes do not support this function temporarily."
        ::= { hwSNMPTrapEnEntry 21 }


    hwMsAisAlarmEn OBJECT-TYPE
        SYNTAX Integer32 
        MAX-ACCESS read-write
        STATUS current
        DESCRIPTION
            "Reserved nodes do not support this function temporarily."
        ::= { hwSNMPTrapEnEntry 22 }


    hwMsB2SdAlarmEn OBJECT-TYPE
        SYNTAX Integer32 
        MAX-ACCESS read-write
        STATUS current
        DESCRIPTION
            "Reserved nodes do not support this function temporarily."
        ::= { hwSNMPTrapEnEntry 23 }


    hwHpJ1TimAlarmEn OBJECT-TYPE
        SYNTAX Integer32 
        MAX-ACCESS read-write
        STATUS current
        DESCRIPTION
            "Reserved nodes do not support this function temporarily."
        ::= { hwSNMPTrapEnEntry 24 }


    hwHpUneqAlarmEn OBJECT-TYPE
        SYNTAX Integer32 
        MAX-ACCESS read-write
        STATUS current
        DESCRIPTION
            "Reserved nodes do not support this function temporarily."
        ::= { hwSNMPTrapEnEntry 25 }


    hwHpRdiAlarmEn OBJECT-TYPE
        SYNTAX Integer32 
        MAX-ACCESS read-write
        STATUS current
        DESCRIPTION
            "Reserved nodes do not support this function temporarily."
        ::= { hwSNMPTrapEnEntry 26 }


    hwHpB3ExcAlarmEn OBJECT-TYPE
        SYNTAX Integer32 
        MAX-ACCESS read-write
        STATUS current
        DESCRIPTION
            "Reserved nodes do not support this function temporarily."
        ::= { hwSNMPTrapEnEntry 27 }


    hwHpPlmAlarmEn OBJECT-TYPE
        SYNTAX Integer32 
        MAX-ACCESS read-write
        STATUS current
        DESCRIPTION
            "Reserved nodes do not support this function temporarily."
        ::= { hwSNMPTrapEnEntry 28 }


    hwHpB3SdAlarmEn OBJECT-TYPE
        SYNTAX Integer32 
        MAX-ACCESS read-write
        STATUS current
        DESCRIPTION
            "Reserved nodes do not support this function temporarily."
        ::= { hwSNMPTrapEnEntry 29 }


    hwHpAuAisAlarmEn OBJECT-TYPE
        SYNTAX Integer32 
        MAX-ACCESS read-write
        STATUS current
        DESCRIPTION
            "Reserved nodes do not support this function temporarily."
        ::= { hwSNMPTrapEnEntry 30 }


    hwLpTuLopAlarmEn OBJECT-TYPE
        SYNTAX Integer32 
        MAX-ACCESS read-write
        STATUS current
        DESCRIPTION
            "Reserved nodes do not support this function temporarily."
        ::= { hwSNMPTrapEnEntry 31 }


    hwHpTuLomAlarmEn OBJECT-TYPE
        SYNTAX Integer32 
        MAX-ACCESS read-write
        STATUS current
        DESCRIPTION
            "Reserved nodes do not support this function temporarily."
        ::= { hwSNMPTrapEnEntry 32 }


    hwLpTimAlarmEn OBJECT-TYPE
        SYNTAX Integer32 
        MAX-ACCESS read-write
        STATUS current
        DESCRIPTION
            "Reserved nodes do not support this function temporarily."
        ::= { hwSNMPTrapEnEntry 33 }


    hwLpUneqAlarmEn OBJECT-TYPE
        SYNTAX Integer32 
        MAX-ACCESS read-write
        STATUS current
        DESCRIPTION
            "Reserved nodes do not support this function temporarily."
        ::= { hwSNMPTrapEnEntry 34 }


    hwLpRdiAlarmEn OBJECT-TYPE
        SYNTAX Integer32 
        MAX-ACCESS read-write
        STATUS current
        DESCRIPTION
            "Reserved nodes do not support this function temporarily."
        ::= { hwSNMPTrapEnEntry 35 }


    hwLpBipExcAlarmEn OBJECT-TYPE
        SYNTAX Integer32 
        MAX-ACCESS read-write
        STATUS current
        DESCRIPTION
            "Reserved nodes do not support this function temporarily."
        ::= { hwSNMPTrapEnEntry 36 }


    hwLpBipSdAlarmEn OBJECT-TYPE
        SYNTAX Integer32 
        MAX-ACCESS read-write
        STATUS current
        DESCRIPTION
            "Reserved nodes do not support this function temporarily."
        ::= { hwSNMPTrapEnEntry 37 }


    hwLpPlmAlarmEn OBJECT-TYPE
        SYNTAX Integer32 
        MAX-ACCESS read-write
        STATUS current
        DESCRIPTION
            "Reserved nodes do not support this function temporarily."
        ::= { hwSNMPTrapEnEntry 38 }


    hwLpTuAisAlarmEn OBJECT-TYPE
        SYNTAX Integer32 
        MAX-ACCESS read-write
        STATUS current
        DESCRIPTION
            "Reserved nodes do not support this function temporarily."
        ::= { hwSNMPTrapEnEntry 39 }


    hwDs1EsExcAlarmEn OBJECT-TYPE
        SYNTAX Integer32 
        MAX-ACCESS read-write
        STATUS current
        DESCRIPTION
            "Reserved nodes do not support this function temporarily."
        ::= { hwSNMPTrapEnEntry 40 }


    hwDs1RmfaAlarmEn OBJECT-TYPE
        SYNTAX Integer32 
        MAX-ACCESS read-write
        STATUS current
        DESCRIPTION
            "Reserved nodes do not support this function temporarily."
        ::= { hwSNMPTrapEnEntry 41 }


    hwDs1LmfaAlarmEn OBJECT-TYPE
        SYNTAX Integer32 
        MAX-ACCESS read-write
        STATUS current
        DESCRIPTION
            "Reserved nodes do not support this function temporarily."
        ::= { hwSNMPTrapEnEntry 42 }


    hwDs1AisAlarmEn OBJECT-TYPE
        SYNTAX Integer32 
        MAX-ACCESS read-write
        STATUS current
        DESCRIPTION
            "Reserved nodes do not support this function temporarily."
        ::= { hwSNMPTrapEnEntry 43 }


    hwDs1RdiAlarmEn OBJECT-TYPE
        SYNTAX Integer32 
        MAX-ACCESS read-write
        STATUS current
        DESCRIPTION
            "Reserved nodes do not support this function temporarily."
        ::= { hwSNMPTrapEnEntry 44 }


    hwRsLocAlarmEn OBJECT-TYPE
        SYNTAX Integer32 
        MAX-ACCESS read-write
        STATUS current
        DESCRIPTION
            "Reserved nodes do not support this function temporarily."
        ::= { hwSNMPTrapEnEntry 45 }


    hwLpRfiAlarmEn OBJECT-TYPE
        SYNTAX Integer32 
        MAX-ACCESS read-write
        STATUS current
        DESCRIPTION
            "Reserved nodes do not support this function temporarily."
        ::= { hwSNMPTrapEnEntry 46 }


    hwLpV5VcaisAlarmEn OBJECT-TYPE
        SYNTAX Integer32 
        MAX-ACCESS read-write
        STATUS current
        DESCRIPTION
            "Reserved nodes do not support this function temporarily."
        ::= { hwSNMPTrapEnEntry 47 }


    hwVc12oofAlarmEn OBJECT-TYPE
        SYNTAX Integer32 
        MAX-ACCESS read-write
        STATUS current
        DESCRIPTION
            "Reserved nodes do not support this function temporarily."
        ::= { hwSNMPTrapEnEntry 48 }


    hwVc12AlmE1RaiAlarmEn OBJECT-TYPE
        SYNTAX Integer32 
        MAX-ACCESS read-write
        STATUS current
        DESCRIPTION
            "Reserved nodes do not support this function temporarily."
        ::= { hwSNMPTrapEnEntry 49 }


    hwVc12LfaAlarmEn OBJECT-TYPE
        SYNTAX Integer32 
        MAX-ACCESS read-write
        STATUS current
        DESCRIPTION
            "Reserved nodes do not support this function temporarily."
        ::= { hwSNMPTrapEnEntry 50 }


    hwVc12UpE1AisAlarmEn OBJECT-TYPE
        SYNTAX Integer32 
        MAX-ACCESS read-write
        STATUS current
        DESCRIPTION
            "Reserved nodes do not support this function temporarily."
        ::= { hwSNMPTrapEnEntry 51 }


    hwVc12DownE1AisAlarmEn OBJECT-TYPE
        SYNTAX Integer32 
        MAX-ACCESS read-write
        STATUS current
        DESCRIPTION
            "Reserved nodes do not support this function temporarily."
        ::= { hwSNMPTrapEnEntry 52 }


    hwDs1DownE1AisAlarmEn OBJECT-TYPE
        SYNTAX Integer32 
        MAX-ACCESS read-write
        STATUS current
        DESCRIPTION
            "Reserved nodes do not support this function temporarily."
        ::= { hwSNMPTrapEnEntry 53 }


    hwMsLpsUniBiMAlarmEn OBJECT-TYPE
        SYNTAX Integer32 
        MAX-ACCESS read-write
        STATUS current
        DESCRIPTION
            "Reserved nodes do not support this function temporarily."
        ::= { hwSNMPTrapEnEntry 54 }


    hwMsK1K2MAlarmEn OBJECT-TYPE
        SYNTAX Integer32 
        MAX-ACCESS read-write
        STATUS current
        DESCRIPTION
            "Reserved nodes do not support this function temporarily."
        ::= { hwSNMPTrapEnEntry 55 }


    hwMsK2MAlarmEn OBJECT-TYPE
        SYNTAX Integer32 
        MAX-ACCESS read-write
        STATUS current
        DESCRIPTION
            "Reserved nodes do not support this function temporarily."
        ::= { hwSNMPTrapEnEntry 56 }


    hwVc12LmfaAlarmEn OBJECT-TYPE
        SYNTAX Integer32 
        MAX-ACCESS read-write
        STATUS current
        DESCRIPTION
            "Reserved nodes do not support this function temporarily."
        ::= { hwSNMPTrapEnEntry 57 }


    hwSDHAllEn OBJECT-TYPE
        SYNTAX Integer32 
        MAX-ACCESS read-write
        STATUS current
        DESCRIPTION
            "Reserved nodes do not support this function temporarily."
        ::= { hwSNMPTrapEnEntry 58 }


    hwLaserShutAlarmEn OBJECT-TYPE
        SYNTAX Integer32 
        MAX-ACCESS read-write
        STATUS current
        DESCRIPTION
            "Reserved nodes do not support this function temporarily."
        ::= { hwSNMPTrapEnEntry 59 }


    hwLaserAutoShutAlarmEn OBJECT-TYPE
        SYNTAX Integer32 
        MAX-ACCESS read-write
        STATUS current
        DESCRIPTION
            "Reserved nodes do not support this function temporarily."
        ::= { hwSNMPTrapEnEntry 60 }


    hwLaserAllEn OBJECT-TYPE
        SYNTAX Integer32 
        MAX-ACCESS read-write
        STATUS current
        DESCRIPTION
            "Reserved nodes do not support this function temporarily."
        ::= { hwSNMPTrapEnEntry 61 }


    hwLoopbackAlarmEn OBJECT-TYPE
        SYNTAX Integer32 
        MAX-ACCESS read-write
        STATUS current
        DESCRIPTION
            "Reserved nodes do not support this function temporarily."
        ::= { hwSNMPTrapEnEntry 62 }


    hwChannelLoopbackAlarmEn OBJECT-TYPE
        SYNTAX Integer32 
        MAX-ACCESS read-write
        STATUS current
        DESCRIPTION
            "Reserved nodes do not support this function temporarily."
        ::= { hwSNMPTrapEnEntry 63 }


    hwLoopbackAllEn OBJECT-TYPE
        SYNTAX Integer32 
        MAX-ACCESS read-write
        STATUS current
        DESCRIPTION
            "Reserved nodes do not support this function temporarily."
        ::= { hwSNMPTrapEnEntry 64 }


    hwAtmOcdAlarmEn OBJECT-TYPE
        SYNTAX Integer32 
        MAX-ACCESS read-write
        STATUS current
        DESCRIPTION
            "Reserved nodes do not support this function temporarily."
        ::= { hwSNMPTrapEnEntry 65 }


    hwAtmLcdAlarmEn OBJECT-TYPE
        SYNTAX Integer32 
        MAX-ACCESS read-write
        STATUS current
        DESCRIPTION
            "Reserved nodes do not support this function temporarily."
        ::= { hwSNMPTrapEnEntry 66 }


    hwAtmUhcsAlarmEn OBJECT-TYPE
        SYNTAX Integer32 
        MAX-ACCESS read-write
        STATUS current
        DESCRIPTION
            "Reserved nodes do not support this function temporarily."
        ::= { hwSNMPTrapEnEntry 67 }


    hwAtmChcsAlarmEn OBJECT-TYPE
        SYNTAX Integer32 
        MAX-ACCESS read-write
        STATUS current
        DESCRIPTION
            "Reserved nodes do not support this function temporarily."
        ::= { hwSNMPTrapEnEntry 68 }


    hwAtmPWLosPktEn OBJECT-TYPE
        SYNTAX Integer32 
        MAX-ACCESS read-write
        STATUS current
        DESCRIPTION
            "Reserved nodes do not support this function temporarily."
        ::= { hwSNMPTrapEnEntry 69 }


    hwAtmPWMisorderPktEn OBJECT-TYPE
        SYNTAX Integer32 
        MAX-ACCESS read-write
        STATUS current
        DESCRIPTION
            "Reserved nodes do not support this function temporarily."
        ::= { hwSNMPTrapEnEntry 70 }


    hwAtmPWUnknownCellEn OBJECT-TYPE
        SYNTAX Integer32 
        MAX-ACCESS read-write
        STATUS current
        DESCRIPTION
            "Reserved nodes do not support this function temporarily."
        ::= { hwSNMPTrapEnEntry 71 }


    hwAtmAllEn OBJECT-TYPE
        SYNTAX Integer32 
        MAX-ACCESS read-write
        STATUS current
        DESCRIPTION
            "Reserved nodes do not support this function temporarily."
        ::= { hwSNMPTrapEnEntry 72 }


    hwPortAlarmThreshold OBJECT IDENTIFIER ::= { hwPortMIBObjects 14 }

    hwPortAlarmThresholdTable OBJECT-TYPE
        SYNTAX  SEQUENCE OF HwPortAlarmThresholdEntry
        MAX-ACCESS not-accessible
        STATUS current
        DESCRIPTION
            "This table describes alarm statistics and alarm thresholds on interfaces."
        ::= { hwPortAlarmThreshold 1 }


    hwPortAlarmThresholdEntry OBJECT-TYPE
        SYNTAX HwPortAlarmThresholdEntry 
        MAX-ACCESS not-accessible
        STATUS current
        DESCRIPTION
            "Indicates the port alarm threshold.
                This table lists the threshold of various port alarm."
        INDEX { hwPhysicalPortThrIfIndex }
        ::= { hwPortAlarmThresholdTable 1 }


    HwPortAlarmThresholdEntry ::= SEQUENCE {
        hwPhysicalPortThrIfIndex 
            InterfaceIndex,
        hwPhysicalPortThrName 
            OCTET STRING,
        hwPhysicalPortCrcErrorStatistics 
            Counter64,
        hwPhysicalPortCrcErrorHighThreshold 
            Unsigned32,
        hwPhysicalPortCrcErrorLowThreshold 
            Unsigned32,
        hwPhysicalPortCrcErrorInterval 
            Unsigned32,
        hwPhysicalPortSymbolErrorStatistics 
            Counter64,
        hwPhysicalPortSymbolErrorHighThreshold 
            Unsigned32,
        hwPhysicalPortSymbolErrorLowThreshold 
            Unsigned32,
        hwPhysicalPortSymbolErrorInterval 
            Unsigned32,
        hwPhysicalPortInputErrorStatistics 
            Counter64,
        hwPhysicalPortInputErrorHighThreshold 
            Unsigned32,
        hwPhysicalPortInputErrorLowThreshold 
            Unsigned32,
        hwPhysicalPortInputErrorInterval 
            Unsigned32,
        hwPhysicalPortOutputErrorStatistics 
            Counter64,
        hwPhysicalPortOutputErrorHighThreshold 
            Unsigned32,
        hwPhysicalPortOutputErrorLowThreshold 
            Unsigned32,
        hwPhysicalPortOutputErrorInterval 
            Unsigned32,
        hwPhysicalPortSdhErrorStatistics 
            Counter64,
        hwPhysicalPortSdhErrorHighThreshold 
            Unsigned32,
        hwPhysicalPortSdhErrorLowThreshold 
            Unsigned32,
        hwPhysicalPortSdhErrorInterval 
            Unsigned32,
        hwPhysicalPortBIP8SDErrorThreshold 
            Unsigned32,
        hwPhysicalPortCrcPerAlarmThresholdCoefficient 
            Unsigned32,
        hwPhysicalPortCrcPerAlarmThresholdPower 
            Unsigned32,
        hwPhysicalPortCrcPerResumeThresholdCoefficient 
            Unsigned32,
        hwPhysicalPortCrcPerResumeThresholdPower 
            Unsigned32,
        hwPhysicalPortCrcPerTriggerLsp 
            Unsigned32,
        hwPhysicalPortCrcPerCurrentValueString 
            OCTET STRING,
        hwPhysicalPortCrcPerAlarmThresholdString 
            OCTET STRING,
        hwPhysicalPortCrcPerResumeThresholdString 
            OCTET STRING,
        hwPhysicalPortCrcPerTriggerSection 
            Unsigned32,
        hwPhysicalPortAlarmTypeThresholdCoefficient 
            INTEGER,
        hwPhysicalPortCrcSdAlarmThresholdCoefficient 
            Unsigned32,
        hwPhysicalPortCrcSdAlarmThresholdPower 
            Unsigned32,
        hwPhysicalPortCrcSdResumeThresholdCoefficient 
            Unsigned32,
        hwPhysicalPortCrcSdResumeThresholdPower 
            Unsigned32,
        hwPhysicalPortCrcExcAlarmThresholdCoefficient 
            Unsigned32,
        hwPhysicalPortCrcExcAlarmThresholdPower 
            Unsigned32,
        hwPhysicalPortCrcExcResumeThresholdCoefficient 
            Unsigned32,
        hwPhysicalPortCrcExcResumeThresholdPower 
            Unsigned32,
        hwPhysicalPortCrcSdAlarmThresholdString 
            OCTET STRING,
        hwPhysicalPortCrcSdResumeThresholdString 
            OCTET STRING,
        hwPhysicalPortCrcExcAlarmThresholdString 
            OCTET STRING,
        hwPhysicalPortCrcExcResumeThresholdString 
            OCTET STRING,
        hwPhysicalPortCrcPerAlarmCoefficientStatistics 
            Unsigned32,
        hwPhysicalPortCrcPerAlarmPowerStatistics 
            Unsigned32,
        hwPhysicalPortCrcSdAlarmTriggerLsp
            INTEGER,
        hwPhysicalPortCrcExcAlarmTriggerLsp
            INTEGER,
        hwPhysicalPortCrcPerWarningThresholdCoefficient 
            Unsigned32,
        hwPhysicalPortCrcPerWarningThresholdPower 
            Unsigned32,
        hwPhysicalPortCrcPerWarningResumeThresholdCoefficient 
            Unsigned32,
        hwPhysicalPortCrcPerWarningResumeThresholdPower 
            Unsigned32,
        hwPhysicalPortCrcPerWarningThresholdString 
            OCTET STRING,
        hwPhysicalPortCrcPerWarningResumeThresholdString 
            OCTET STRING,
        hwPhysicalPortPreFecCoefficientStatistics
            Unsigned32,
        hwPhysicalPortPreFecPowerStatistics 
            Unsigned32,
        hwPhysicalPortErrorPerCurrentValueString
            OCTET STRING,
        hwPhysicalPortErrorPerAlarmThresholdString
            OCTET STRING,
		hwInputBroadcastChangeThreshold
            Unsigned32,
		hwCurrentStatisticalInputBroadcast
			Counter64,
		hwBaseStatisticalInputBroadcast
			Counter64		
             }

    hwPhysicalPortThrIfIndex OBJECT-TYPE
        SYNTAX InterfaceIndex 
        MAX-ACCESS accessible-for-notify
        STATUS current
        DESCRIPTION
            "This object indicates the index of a physical interface."
        ::= { hwPortAlarmThresholdEntry 1 }


    hwPhysicalPortThrName OBJECT-TYPE
        SYNTAX OCTET STRING (SIZE (0..64))
        MAX-ACCESS read-only
        STATUS current
        DESCRIPTION
            "This object indicates the name of a physical interface."
        ::= { hwPortAlarmThresholdEntry 2 }


    hwPhysicalPortCrcErrorStatistics OBJECT-TYPE
        SYNTAX Counter64 
        MAX-ACCESS read-only
        STATUS current
        DESCRIPTION
            "This object indicates the CRC error statistics."
        ::= { hwPortAlarmThresholdEntry 3 }


    hwPhysicalPortCrcErrorHighThreshold OBJECT-TYPE
        SYNTAX Unsigned32 (0..4294967295)
        MAX-ACCESS read-write
        STATUS current
        DESCRIPTION
            "This object indicates the upper threshold for the number of CRC errors. The default value is 1000 pps."
        ::= { hwPortAlarmThresholdEntry 4 }


    hwPhysicalPortCrcErrorLowThreshold OBJECT-TYPE
        SYNTAX Unsigned32 (0..4294967295)
        MAX-ACCESS read-write
        STATUS current
        DESCRIPTION
            "This object indicates the lower threshold for the number of CRC errors. The default value is 100 pps."
        ::= { hwPortAlarmThresholdEntry 5 }


    hwPhysicalPortCrcErrorInterval OBJECT-TYPE
        SYNTAX Unsigned32 (1..65535)
        MAX-ACCESS read-write
        STATUS current
        DESCRIPTION
            "This object indicates the time threshold for the CRC error alarm. The default value is 10s."
        ::= { hwPortAlarmThresholdEntry 6 }


    hwPhysicalPortSymbolErrorStatistics OBJECT-TYPE
        SYNTAX Counter64 
        MAX-ACCESS read-only
        STATUS current
        DESCRIPTION
            "This object indicates the number of Symbol errors."
        ::= { hwPortAlarmThresholdEntry 7 }


    hwPhysicalPortSymbolErrorHighThreshold OBJECT-TYPE
        SYNTAX Unsigned32 (0..4294967295)
        MAX-ACCESS read-write
        STATUS current
        DESCRIPTION
            "This object indicates the upper threshold for the number of Symbol errors. The default value is 1000 pps."
        ::= { hwPortAlarmThresholdEntry 8 }


    hwPhysicalPortSymbolErrorLowThreshold OBJECT-TYPE
        SYNTAX Unsigned32 (0..4294967295)
        MAX-ACCESS read-write
        STATUS current
        DESCRIPTION
            "This object indicates the lower threshold for the number of Symbol errors. The default value is 100 pps."
        ::= { hwPortAlarmThresholdEntry 9 }


    hwPhysicalPortSymbolErrorInterval OBJECT-TYPE
        SYNTAX Unsigned32 (1..65535)
        MAX-ACCESS read-write
        STATUS current
        DESCRIPTION
            "This object indicates the time threshold for the Symbol error alarm. The default value is 10s."
        ::= { hwPortAlarmThresholdEntry 10 }


    hwPhysicalPortInputErrorStatistics OBJECT-TYPE
        SYNTAX Counter64 
        MAX-ACCESS read-only
        STATUS current
        DESCRIPTION
            "This object indicates the number of Input errors."
        ::= { hwPortAlarmThresholdEntry 11 }


    hwPhysicalPortInputErrorHighThreshold OBJECT-TYPE
        SYNTAX Unsigned32 (0..4294967295)
        MAX-ACCESS read-write
        STATUS current
        DESCRIPTION
            "This object indicates the upper threshold for the number of Input errors. The default value is 1000 pps."
        ::= { hwPortAlarmThresholdEntry 12 }


    hwPhysicalPortInputErrorLowThreshold OBJECT-TYPE
        SYNTAX Unsigned32 (0..4294967295)
        MAX-ACCESS read-write
        STATUS current
        DESCRIPTION
            "This object indicates the lower threshold for the number of Input errors. The default value is 100 pps."
        ::= { hwPortAlarmThresholdEntry 13 }


    hwPhysicalPortInputErrorInterval OBJECT-TYPE
        SYNTAX Unsigned32 (1..65535)
        MAX-ACCESS read-write
        STATUS current
        DESCRIPTION
            "This object indicates the time threshold for the Input error alarm. The default value is 10s."
        ::= { hwPortAlarmThresholdEntry 14 }


    hwPhysicalPortOutputErrorStatistics OBJECT-TYPE
        SYNTAX Counter64 
        MAX-ACCESS read-only
        STATUS current
        DESCRIPTION
            "This object indicates the number of Output errors."
        ::= { hwPortAlarmThresholdEntry 15 }


    hwPhysicalPortOutputErrorHighThreshold OBJECT-TYPE
        SYNTAX Unsigned32 (0..4294967295)
        MAX-ACCESS read-write
        STATUS current
        DESCRIPTION
            "This object indicates the upper threshold for the number of Output errors. The default value is 1000 pps."
        ::= { hwPortAlarmThresholdEntry 16 }


    hwPhysicalPortOutputErrorLowThreshold OBJECT-TYPE
        SYNTAX Unsigned32 (0..4294967295)
        MAX-ACCESS read-write
        STATUS current
        DESCRIPTION
            "This object indicates the lower threshold for the number of Output errors. The default value is 100 pps."
        ::= { hwPortAlarmThresholdEntry 17 }


    hwPhysicalPortOutputErrorInterval OBJECT-TYPE
        SYNTAX Unsigned32 (1..65535)
        MAX-ACCESS read-write
        STATUS current
        DESCRIPTION
            "This object indicates the time threshold for the Output error alarm. The default value is 10s."
        ::= { hwPortAlarmThresholdEntry 18 }


    hwPhysicalPortSdhErrorStatistics OBJECT-TYPE
        SYNTAX Counter64 
        MAX-ACCESS read-only
        STATUS current
        DESCRIPTION
            "This object indicates the number of SDH errors."
        ::= { hwPortAlarmThresholdEntry 19 }


    hwPhysicalPortSdhErrorHighThreshold OBJECT-TYPE
        SYNTAX Unsigned32 (0..4294967295)
        MAX-ACCESS read-write
        STATUS current
        DESCRIPTION
            "This object indicates the upper threshold for the number of SDH errors. The default value is 1000 pps."
        ::= { hwPortAlarmThresholdEntry 20 }


    hwPhysicalPortSdhErrorLowThreshold OBJECT-TYPE
        SYNTAX Unsigned32 (0..4294967295)
        MAX-ACCESS read-write
        STATUS current
        DESCRIPTION
            "This object indicates the lower threshold for the number of SDH errors. The default value is 100 pps."
        ::= { hwPortAlarmThresholdEntry 21 }


    hwPhysicalPortSdhErrorInterval OBJECT-TYPE
        SYNTAX Unsigned32 (1..65535)
        MAX-ACCESS read-write
        STATUS current
        DESCRIPTION
            "This object indicates the time threshold for the SDH error alarm. The default value is 10s."
        ::= { hwPortAlarmThresholdEntry 22 }


    hwPhysicalPortBIP8SDErrorThreshold OBJECT-TYPE
        SYNTAX Unsigned32 (6..9)
        MAX-ACCESS read-write
        STATUS current
        DESCRIPTION
            "This object indicates the BIP8 SD alarm threshold. The default value is 6."
        ::= { hwPortAlarmThresholdEntry 23 }


    hwPhysicalPortCrcPerAlarmThresholdCoefficient OBJECT-TYPE
        SYNTAX Unsigned32 
        MAX-ACCESS read-write
        STATUS current
        DESCRIPTION
            "This object indicates the coefficient x in the (xE-y) alarm threshold for the CRC error packet ratio on a physical interface."
        ::= { hwPortAlarmThresholdEntry 24 }


    hwPhysicalPortCrcPerAlarmThresholdPower OBJECT-TYPE
        SYNTAX Unsigned32 
        MAX-ACCESS read-write
        STATUS current
        DESCRIPTION
            "This object indicates the power y in the (xE-y) alarm threshold for the CRC error packet ratio on a physical interface."
        ::= { hwPortAlarmThresholdEntry 25 }


    hwPhysicalPortCrcPerResumeThresholdCoefficient OBJECT-TYPE
        SYNTAX Unsigned32 
        MAX-ACCESS read-write
        STATUS current
        DESCRIPTION
            "This object indicates the coefficient x in the (xE-y) clear alarm threshold for the CRC error packet ratio on a physical interface."
        ::= { hwPortAlarmThresholdEntry 26 }


    hwPhysicalPortCrcPerResumeThresholdPower OBJECT-TYPE
        SYNTAX Unsigned32 
        MAX-ACCESS read-write
        STATUS current
        DESCRIPTION
            "This object indicates the power y in the (xE-y) clear alarm threshold for the CRC error packet ratio on a physical interface."
        ::= { hwPortAlarmThresholdEntry 27 }


    hwPhysicalPortCrcPerTriggerLsp OBJECT-TYPE
        SYNTAX Unsigned32 
        MAX-ACCESS read-write
        STATUS current
        DESCRIPTION
            "This object indicates whether the CRC error packet ratio alarm and its clear alarm on a physical interface are associated with LSPs."
        ::= { hwPortAlarmThresholdEntry 28 }


    hwPhysicalPortCrcPerCurrentValueString OBJECT-TYPE
        SYNTAX OCTET STRING 
        MAX-ACCESS accessible-for-notify
        STATUS current
        DESCRIPTION
            "This object indicates that the thresholds for CRC error packet ratio alarms on a physical interface are sent to the NMS in the character string format."
        ::= { hwPortAlarmThresholdEntry 29 }


    hwPhysicalPortCrcPerAlarmThresholdString OBJECT-TYPE
        SYNTAX OCTET STRING 
        MAX-ACCESS accessible-for-notify
        STATUS current
        DESCRIPTION
            "This object indicates that the generation threshold for the CRC error packet ratio alarm on a physical interface is sent to the NMS in the character string format."
        ::= { hwPortAlarmThresholdEntry 30 }


    hwPhysicalPortCrcPerResumeThresholdString OBJECT-TYPE
        SYNTAX OCTET STRING 
        MAX-ACCESS accessible-for-notify
        STATUS current
        DESCRIPTION
            "This object indicates that the clearing threshold for the CRC error packet ratio clear alarm on a physical interface is sent to the NMS in the character string format."
        ::= { hwPortAlarmThresholdEntry 31 }


    hwPhysicalPortCrcPerTriggerSection OBJECT-TYPE
        SYNTAX Unsigned32 
        MAX-ACCESS read-write
        STATUS current
        DESCRIPTION
            "This object indicates whether the CRC error packet ratio alarm and its clear alarm on a physical interface are associated with sections."
        ::= { hwPortAlarmThresholdEntry 32 }


    hwPhysicalPortAlarmTypeThresholdCoefficient OBJECT-TYPE
        SYNTAX INTEGER {packeterror(0),packeterrorratio(1),biterrorratio(2)}
        MAX-ACCESS read-write
        STATUS current
        DESCRIPTION
            "0: indicates that the upper and lower thresholds triggering error packet alarms are enabled.
			 1: indicates that the alarm function for CRC error packets is enabled.
			 2: indicates that the alarm function for CRC bit errors is enabled."
        ::= { hwPortAlarmThresholdEntry 33 }


    hwPhysicalPortCrcSdAlarmThresholdCoefficient OBJECT-TYPE
        SYNTAX Unsigned32 
        MAX-ACCESS read-write
        STATUS current
        DESCRIPTION
            "The coefficient value of MAC_FCS_SD alarm threshold. The range is 1 to 9."
        ::= { hwPortAlarmThresholdEntry 34 }


    hwPhysicalPortCrcSdAlarmThresholdPower OBJECT-TYPE
        SYNTAX Unsigned32 
        MAX-ACCESS read-write
        STATUS current
        DESCRIPTION
            "The power value of MAC_FCS_SD alarm threshold. The range is 5 to 9."
        ::= { hwPortAlarmThresholdEntry 35 }


    hwPhysicalPortCrcSdResumeThresholdCoefficient OBJECT-TYPE
        SYNTAX Unsigned32 
        MAX-ACCESS read-write
        STATUS current
        DESCRIPTION
            "The coefficient value of MAC_FCS_SD resume threshold. The range is 1 to 9."
        ::= { hwPortAlarmThresholdEntry 36 }


    hwPhysicalPortCrcSdResumeThresholdPower OBJECT-TYPE
        SYNTAX Unsigned32 
        MAX-ACCESS read-write
        STATUS current
        DESCRIPTION
            "The power value of MAC_FCS_SD resume threshold. The range is 5 to 9."
        ::= { hwPortAlarmThresholdEntry 37 }


    hwPhysicalPortCrcExcAlarmThresholdCoefficient OBJECT-TYPE
        SYNTAX Unsigned32 
        MAX-ACCESS read-write
        STATUS current
        DESCRIPTION
            "The coefficient value of MAC_FCS_EXC alarm threshold. The range is 1 to 9."
        ::= { hwPortAlarmThresholdEntry 38 }


    hwPhysicalPortCrcExcAlarmThresholdPower OBJECT-TYPE
        SYNTAX Unsigned32 
        MAX-ACCESS read-write
        STATUS current
        DESCRIPTION
            "The power value of MAC_FCS_EXC alarm threshold. The range is 2 to 5."
        ::= { hwPortAlarmThresholdEntry 39 }


    hwPhysicalPortCrcExcResumeThresholdCoefficient OBJECT-TYPE
        SYNTAX Unsigned32 
        MAX-ACCESS read-write
        STATUS current
        DESCRIPTION
            "The coefficient value of MAC_FCS_EXC resume threshold. The range is 1 to 9."
        ::= { hwPortAlarmThresholdEntry 40 }


    hwPhysicalPortCrcExcResumeThresholdPower OBJECT-TYPE
        SYNTAX Unsigned32 
        MAX-ACCESS read-write
        STATUS current
        DESCRIPTION
            "The power value of MAC_FCS_EXC resume threshold. The range is 2 to 5."
        ::= { hwPortAlarmThresholdEntry 41 }



    hwPhysicalPortCrcSdAlarmThresholdString OBJECT-TYPE
        SYNTAX OCTET STRING 
        MAX-ACCESS accessible-for-notify
        STATUS current
        DESCRIPTION
            "The alarm threshold of MAC_FCS_SD."
        ::= { hwPortAlarmThresholdEntry 42 }


    hwPhysicalPortCrcSdResumeThresholdString OBJECT-TYPE
        SYNTAX OCTET STRING 
        MAX-ACCESS accessible-for-notify
        STATUS current
        DESCRIPTION
            "The resume threshold of MAC_FCS_SD."
        ::= { hwPortAlarmThresholdEntry 43 }


    hwPhysicalPortCrcExcAlarmThresholdString OBJECT-TYPE
        SYNTAX OCTET STRING 
        MAX-ACCESS accessible-for-notify
        STATUS current
        DESCRIPTION
            "The alarm threshold of MAC_FCS_EXC."
        ::= { hwPortAlarmThresholdEntry 44 }


    hwPhysicalPortCrcExcResumeThresholdString OBJECT-TYPE
        SYNTAX OCTET STRING 
        MAX-ACCESS accessible-for-notify
        STATUS current
        DESCRIPTION
            "The resume threshold of MAC_FCS_EXC."
        ::= { hwPortAlarmThresholdEntry 45 }

    hwPhysicalPortCrcPerAlarmCoefficientStatistics OBJECT-TYPE
        SYNTAX Unsigned32 
        MAX-ACCESS read-only
        STATUS current
        DESCRIPTION
            "The coefficient value of CRC-PER(Packet Error Ratio) alarm statistics."
        ::= { hwPortAlarmThresholdEntry 46 }

    hwPhysicalPortCrcPerAlarmPowerStatistics OBJECT-TYPE
        SYNTAX Unsigned32 
        MAX-ACCESS read-only
        STATUS current
        DESCRIPTION
            "The power value of CRC-PER(Packet Error Ratio) alarm statistics."
        ::= { hwPortAlarmThresholdEntry 47 }
	
    -- 1.3.6.1.4.1.2011.5.25.157.1.14.1.1.48
    hwPhysicalPortCrcSdAlarmTriggerLsp OBJECT-TYPE
	SYNTAX INTEGER
		{
		notsupport(-1),
		enable(1),
		disable(2)
		}
	MAX-ACCESS read-write
	STATUS current
	DESCRIPTION
		"Enable or disable the SD alarm result in switchover.
		The value -1 means do not support switchover;1 means the lsp switchover is enabled; 2 means  switchover is disabled. 
		"
	::= { hwPortAlarmThresholdEntry 48 }

		
    -- 1.3.6.1.4.1.2011.5.25.157.1.14.1.1.49
    hwPhysicalPortCrcExcAlarmTriggerLsp OBJECT-TYPE
    SYNTAX INTEGER
        {
        notsupport(-1),
        enable(1),
        disable(2)
        }
    MAX-ACCESS read-write
    STATUS current
    DESCRIPTION
        "Enable or disable the EXC alarm result in switchover.
        The value -1 means do not support switchover;1 means the lsp  switchover is enabled; 2 means switchover is disabled."
    ::= { hwPortAlarmThresholdEntry 49 }

    -- 1.3.6.1.4.1.2011.5.25.157.1.14.1.1.50
    hwPhysicalPortCrcPerWarningThresholdCoefficient OBJECT-TYPE
        SYNTAX Unsigned32 
        MAX-ACCESS read-write
        STATUS current
        DESCRIPTION
            "The coefficient value of CRC-PER(Packet Error Ratio) warning threshold. The range is 1 to 9."
        ::= { hwPortAlarmThresholdEntry 50 }

    -- 1.3.6.1.4.1.2011.5.25.157.1.14.1.1.51
    hwPhysicalPortCrcPerWarningThresholdPower OBJECT-TYPE
        SYNTAX Unsigned32 
        MAX-ACCESS read-write
        STATUS current
        DESCRIPTION
            "The power value of CRC-PER(Packet Error Ratio) warning threshold. The range is 1 to 7."
        ::= { hwPortAlarmThresholdEntry 51 }

    -- 1.3.6.1.4.1.2011.5.25.157.1.14.1.1.52
    hwPhysicalPortCrcPerWarningResumeThresholdCoefficient OBJECT-TYPE
        SYNTAX Unsigned32 
        MAX-ACCESS read-write
        STATUS current
        DESCRIPTION
            "The coefficient value of CRC-PER(Packet Error Ratio) warning resume threshold. The range is 1 to 9."
        ::= { hwPortAlarmThresholdEntry 52 }

    -- 1.3.6.1.4.1.2011.5.25.157.1.14.1.1.53
    hwPhysicalPortCrcPerWarningResumeThresholdPower OBJECT-TYPE
        SYNTAX Unsigned32 
        MAX-ACCESS read-write
        STATUS current
        DESCRIPTION
            "The power value of CRC-PER(Packet Error Ratio) warning resume threshold. The range is 1 to 7."
        ::= { hwPortAlarmThresholdEntry 53 }

    -- 1.3.6.1.4.1.2011.5.25.157.1.14.1.1.54
    hwPhysicalPortCrcPerWarningThresholdString OBJECT-TYPE
        SYNTAX OCTET STRING 
        MAX-ACCESS accessible-for-notify
        STATUS current
        DESCRIPTION
            "The warning threshold of CRC-PER(Packet Error Ratio)."
        ::= { hwPortAlarmThresholdEntry 54 }

    -- 1.3.6.1.4.1.2011.5.25.157.1.14.1.1.55
    hwPhysicalPortCrcPerWarningResumeThresholdString OBJECT-TYPE
        SYNTAX OCTET STRING 
        MAX-ACCESS accessible-for-notify
        STATUS current
        DESCRIPTION
            "The warning resume threshold of CRC-PER(Packet Error Ratio)."
        ::= { hwPortAlarmThresholdEntry 55 }

 -- 1.3.6.1.4.1.2011.5.25.157.1.14.1.1.56
    hwPhysicalPortPreFecCoefficientStatistics OBJECT-TYPE
	SYNTAX Unsigned32
	MAX-ACCESS read-only
	STATUS current
	DESCRIPTION
		"The coefficient value of PRE-FEC  bit-error-ratio statistics."
		
	::= { hwPortAlarmThresholdEntry 56 }      

-- 1.3.6.1.4.1.2011.5.25.157.1.14.1.1.57
hwPhysicalPortPreFecPowerStatistics OBJECT-TYPE
	SYNTAX Unsigned32
	MAX-ACCESS read-only
	STATUS current
	DESCRIPTION
		"The power value of PRE-FEC bit-error-ratio statistics."
	::= { hwPortAlarmThresholdEntry 57 }

    hwPhysicalPortErrorPerCurrentValueString OBJECT-TYPE
        SYNTAX OCTET STRING 
        MAX-ACCESS accessible-for-notify
        STATUS current
        DESCRIPTION
            "The current value of error packets per second(Packet Error Ratio)."
        ::= { hwPortAlarmThresholdEntry 58 }

    hwPhysicalPortErrorPerAlarmThresholdString OBJECT-TYPE
        SYNTAX OCTET STRING 
        MAX-ACCESS accessible-for-notify
        STATUS current
        DESCRIPTION
            "The warning threshold of error packets per second(Packet Error Ratio)."
        ::= { hwPortAlarmThresholdEntry 59 }
	
	hwInputBroadcastChangeThreshold OBJECT-TYPE
        SYNTAX Unsigned32
        MAX-ACCESS read-only
        STATUS current
        DESCRIPTION
            "input broadcast rate Threshold."
        ::= { hwPortAlarmThresholdEntry 60 }
	
	hwCurrentStatisticalInputBroadcast OBJECT-TYPE
        SYNTAX Counter64 
        MAX-ACCESS read-only
        STATUS current
        DESCRIPTION
            "current statistics of input broadcast."
        ::= { hwPortAlarmThresholdEntry 61 }
		
	hwBaseStatisticalInputBroadcast OBJECT-TYPE
        SYNTAX Counter64 
        MAX-ACCESS read-only
        STATUS current
        DESCRIPTION
            "base statistics of input broadcast."
        ::= { hwPortAlarmThresholdEntry 62 }
    -- 1.3.6.1.4.1.2011.5.25.157.1.15
    hwPortAlarmDownEnable OBJECT IDENTIFIER ::= { hwPortMIBObjects 15 }

    hwPortAlarmDownEnableTable OBJECT-TYPE
        SYNTAX  SEQUENCE OF HwPortAlarmDownEnableEntry
        MAX-ACCESS not-accessible
        STATUS current
        DESCRIPTION
            "This table describes association between interface alarms and the interface status."
        ::= { hwPortAlarmDownEnable 1 }


    hwPortAlarmDownEnableEntry OBJECT-TYPE
        SYNTAX HwPortAlarmDownEnableEntry 
        MAX-ACCESS not-accessible
        STATUS current
        DESCRIPTION
            "Enalbe or disable the port alarm result in physics down.
                This table lists the enable status of various port alarm."
        INDEX { hwPhysicalPortDownIfIndex }
        ::= { hwPortAlarmDownEnableTable 1 }


    HwPortAlarmDownEnableEntry ::= SEQUENCE {
        hwPhysicalPortDownIfIndex 
            InterfaceIndex,
        hwPhysicalPortDownName 
            OCTET STRING,
        hwPhysicalPortCrcEnabledDown 
            INTEGER,
        hwPhysicalPortSymbolEnabledDown 
            INTEGER,
        hwPhysicalPortInputEnabledDown 
            INTEGER,
        hwPhysicalPortOutputEnabledDown 
            INTEGER,
        hwPhysicalPortSdhEnabledDown 
            INTEGER,
        hwPhysicalPortBip8SdEnabledDown 
            INTEGER
        }


    hwPhysicalPortDownIfIndex OBJECT-TYPE
        SYNTAX InterfaceIndex 
        MAX-ACCESS not-accessible
        STATUS current
        DESCRIPTION
            "This object indicates the interface index."
        ::= { hwPortAlarmDownEnableEntry 1 }


    hwPhysicalPortDownName OBJECT-TYPE
        SYNTAX OCTET STRING (SIZE (0..64))
        MAX-ACCESS read-only
        STATUS current
        DESCRIPTION
            "This object indicates the name of a physical interface."
        ::= { hwPortAlarmDownEnableEntry 2 }


    hwPhysicalPortCrcEnabledDown OBJECT-TYPE
        SYNTAX INTEGER {disable(0),enable(1)}
        MAX-ACCESS read-write
        STATUS current
        DESCRIPTION
            "This object indicates association between the CRC error alarm and the interface status. If a CRC error alarm is generated, the involved interface goes Down accordingly. The default value is disable(0)."
        ::= { hwPortAlarmDownEnableEntry 3 }


    hwPhysicalPortSymbolEnabledDown OBJECT-TYPE
        SYNTAX INTEGER {disable(0),enable(1)}
        MAX-ACCESS read-write
        STATUS current
        DESCRIPTION
            "This object indicates association between the Symbol error alarm and the interface status. If a Symbol error alarm is generated, the involved interface goes Down accordingly. The default value is disable(0)."
        ::= { hwPortAlarmDownEnableEntry 4 }


    hwPhysicalPortInputEnabledDown OBJECT-TYPE
        SYNTAX INTEGER {disable(0),enable(1)}
        MAX-ACCESS read-write
        STATUS current
        DESCRIPTION
            "This object indicates association between the Input error alarm and the interface status. If an Input error alarm is generated, the involved interface goes Down accordingly. The default value is disable(0)."
        ::= { hwPortAlarmDownEnableEntry 5 }


    hwPhysicalPortOutputEnabledDown OBJECT-TYPE
        SYNTAX INTEGER {disable(0),enable(1)}
        MAX-ACCESS read-write
        STATUS current
        DESCRIPTION
            "This object indicates association between the Output error alarm and the interface status. If an Output error alarm is generated, the involved interface goes Down accordingly. The default value is disable(0)."
        ::= { hwPortAlarmDownEnableEntry 6 }


    hwPhysicalPortSdhEnabledDown OBJECT-TYPE
        SYNTAX INTEGER {disable(0),enable(1)}
        MAX-ACCESS read-write
        STATUS current
        DESCRIPTION
            "This object indicates association between the SDH error alarm and the interface status. If an SDH error alarm is generated, the involved interface goes Down accordingly. The default value is disable(0)."
        ::= { hwPortAlarmDownEnableEntry 7 }


    hwPhysicalPortBip8SdEnabledDown OBJECT-TYPE
        SYNTAX INTEGER {disable(0),enable(1)}
        MAX-ACCESS read-write
        STATUS current
        DESCRIPTION
            "Enalbe or disable the BIP8-SD error alarm result in physics down, and the default value is disable."
        ::= { hwPortAlarmDownEnableEntry 8 }


    hwPortProtectGroupCfg OBJECT IDENTIFIER ::= { hwPortMIBObjects 16 }

    hwPortProtectGroupCfgTable OBJECT-TYPE
        SYNTAX  SEQUENCE OF HwPortProtectGroupCfgEntry
        MAX-ACCESS not-accessible
        STATUS current
        DESCRIPTION
            "The table includes the information of the port protect group configuration information,
                and include the port group, working status of port etc."
        ::= { hwPortProtectGroupCfg 1 }


    hwPortProtectGroupCfgEntry OBJECT-TYPE
        SYNTAX HwPortProtectGroupCfgEntry 
        MAX-ACCESS not-accessible
        STATUS current
        DESCRIPTION
            "The table includes the information of the port protect group configuration information.
                The index of the table is hwPortProtectGroupId."
        INDEX { hwPortProtectGroupId }
        ::= { hwPortProtectGroupCfgTable 1 }


    HwPortProtectGroupCfgEntry ::= 
        SEQUENCE {
	        hwPortProtectGroupId 
	            Integer32,
	        hwPortProtectMasterIfIndex
	            Integer32,
	        hwPortProtectMasterStatus 
	            INTEGER,                         
	        hwPortProtectSlaveIfIndex
	            Integer32,
	        hwPortProtectSlaveStatus 
	            INTEGER,                 
	        hwPortProtectRowStatus
	            RowStatus               
	        }
	        
    hwPortProtectGroupId OBJECT-TYPE
        SYNTAX Integer32 (0..127)
        MAX-ACCESS read-only
        STATUS current
        DESCRIPTION
            "Port protect group index."
        ::= { hwPortProtectGroupCfgEntry 1 }

    hwPortProtectMasterIfIndex OBJECT-TYPE
            SYNTAX Integer32
            MAX-ACCESS read-create
            STATUS current
            DESCRIPTION
                "The master interface index of port protect group."
            ::= { hwPortProtectGroupCfgEntry 2 }

    hwPortProtectMasterStatus OBJECT-TYPE
            SYNTAX INTEGER
                { 
                    work(1),
                    protect(2),
                    down(3)
                }
            MAX-ACCESS read-only
            STATUS current            
            DESCRIPTION
                "Working status of master port , include work, protect, down. 
                work: the port in group is active.
                protect: master port is protect port.
                down: master port is inactive."
            ::= { hwPortProtectGroupCfgEntry 3 }   

    hwPortProtectSlaveIfIndex OBJECT-TYPE
            SYNTAX Integer32
            MAX-ACCESS read-create
            STATUS current
            DESCRIPTION
                "The slave interface index of port protect group."
            ::= { hwPortProtectGroupCfgEntry 4 }

    hwPortProtectSlaveStatus OBJECT-TYPE
            SYNTAX INTEGER
                { 
                    work(1),
                    protect(2),
                    down(3)
                }
            MAX-ACCESS read-only
            STATUS current            
            DESCRIPTION
                "Working status of slave port , include work, protect, down. 
                work: the port in group is active.
                protect: slave port is protect port.
                down: slave port is inactive."
            ::= { hwPortProtectGroupCfgEntry 5 }   
                             
    hwPortProtectRowStatus OBJECT-TYPE
            SYNTAX RowStatus
            MAX-ACCESS read-create
            STATUS current
            DESCRIPTION
                "Status of port protect group row."
            ::= { hwPortProtectGroupCfgEntry 6 }  

    hwPortLine OBJECT IDENTIFIER ::= { hwPortMIBObjects 17 }
		
    hwPortLineTable OBJECT-TYPE
	    SYNTAX SEQUENCE OF HwPortLineEntry
	    MAX-ACCESS not-accessible
	    STATUS current
	    DESCRIPTION
		"Indicates the link attributes of the interface.
		 This table lists the link attributes of the interface."
	    ::= { hwPortLine 1 }
		
    hwPortLineEntry OBJECT-TYPE
 	   SYNTAX HwPortLineEntry
	   MAX-ACCESS not-accessible
	   STATUS current
	   DESCRIPTION
	       "Indicates the link attributes of the interface.
	        This table lists the link attributes of the interface."
	   INDEX { hwPortLineIfIndex }
	   ::= { hwPortLineTable 1 }
		
    HwPortLineEntry ::=
	SEQUENCE { 
		hwPortLineIfIndex
		InterfaceIndex,
		hwPortLineUpStreampbo
   		    Integer32,
		hwPortLineDownStreampbo
		    Integer32,
		hwPortLineUpStreamLoopAtten
		    Integer32,
		hwPortLineDownStreamLoopAtten
		    Integer32,
		hwPortLineUpStreamSnrMargin
		    Integer32,
		hwPortLineDownStreamSnrMargin
		    Integer32,
		hwPortLineSpeed
		    Integer32
		 }

    hwPortLineIfIndex OBJECT-TYPE
	SYNTAX InterfaceIndex
	MAX-ACCESS not-accessible
	STATUS current
	DESCRIPTION
  	    "Interface index(es) of port(s) present on the device ."
	::= { hwPortLineEntry 1 }

    hwPortLineUpStreampbo OBJECT-TYPE
	SYNTAX Integer32
	MAX-ACCESS read-only
	STATUS current
	DESCRIPTION
		"Indicates the upstream power back-off of the interface."
	::= { hwPortLineEntry 2 }
		
    hwPortLineDownStreampbo OBJECT-TYPE
	SYNTAX Integer32
	MAX-ACCESS read-only
	STATUS current
	DESCRIPTION
		"Indicates the downstream power back-off of the interface."
	::= { hwPortLineEntry 3 }

    hwPortLineUpStreamLoopAtten OBJECT-TYPE
	SYNTAX Integer32
	MAX-ACCESS read-only
	STATUS current
	DESCRIPTION
	        "Indicates the upstream loopback attenuation of the interface."
	::= { hwPortLineEntry 4 }

    hwPortLineDownStreamLoopAtten OBJECT-TYPE
	SYNTAX Integer32
	MAX-ACCESS read-only
	STATUS current
	DESCRIPTION
    	         "Indicates the downstream loopback attenuation of the interface."
	::= { hwPortLineEntry 5 }

    hwPortLineUpStreamSnrMargin OBJECT-TYPE
	SYNTAX Integer32
	MAX-ACCESS read-only
	STATUS current
	DESCRIPTION
		"Indicates the upstream SNR margin of the interface."
	::= { hwPortLineEntry 6 }

    hwPortLineDownStreamSnrMargin OBJECT-TYPE
	SYNTAX Integer32
	MAX-ACCESS read-only
	STATUS current
	DESCRIPTION
		"Indicates the downstream SNR margin of the interface."
	::= { hwPortLineEntry 7 }

    hwPortLineSpeed OBJECT-TYPE
	SYNTAX Integer32
	MAX-ACCESS read-only
	STATUS current
	DESCRIPTION
		"Indicates the negotiated rate of the interface."
    ::= { hwPortLineEntry 8 }
		
    hwPortIfStatistics OBJECT IDENTIFIER ::= { hwPortMIBObjects 18 }
      
    hwPortIfStatTable OBJECT-TYPE
	SYNTAX SEQUENCE OF HwPortIfStatEntry
	MAX-ACCESS not-accessible
	STATUS current
	DESCRIPTION
		"This table lists the number of packets of the interface."
	::= { hwPortIfStatistics 1 }
		
    hwPortIfStatEntry OBJECT-TYPE
	SYNTAX HwPortIfStatEntry
	MAX-ACCESS not-accessible
	STATUS current
	DESCRIPTION
    	        "This table lists the number of packets of the interface."
	INDEX { hwPortIfStatIfIndex }
	::= { hwPortIfStatTable 1 }
		
    HwPortIfStatEntry ::=
	SEQUENCE { 
		hwPortIfStatIfIndex
	   	    InterfaceIndex,
		hwPortIfStatIfInCrcPkts
		    Integer32
	         }   

    hwPortIfStatIfIndex OBJECT-TYPE
	SYNTAX InterfaceIndex
	MAX-ACCESS not-accessible
	STATUS current
	DESCRIPTION
  	    "Interface index(es) of port(s) present on the device ."
			::= { hwPortIfStatEntry 1 }

    hwPortIfStatIfInCrcPkts OBJECT-TYPE
	SYNTAX Integer32
	MAX-ACCESS read-only
	STATUS current
	DESCRIPTION
	    "Indicates the number of packets which the CRC operates."
			::= { hwPortIfStatEntry 2 } 
			
	hwIPIfStatTable OBJECT-TYPE
	SYNTAX SEQUENCE OF HwIPIfStatEntry
	MAX-ACCESS not-accessible
	STATUS current
	DESCRIPTION
		"This table lists the number of ip packets of the interface."
	::= { hwPortIfStatistics 2 }
		
    hwIPIfStatEntry OBJECT-TYPE
	SYNTAX HwIPIfStatEntry
	MAX-ACCESS not-accessible
	STATUS current
	DESCRIPTION
    	        "This table lists the number of ip packets of the interface."
	INDEX { hwIpIfStatsIfIndex,hwIpIfStatsIPVersion }
	::= { hwIPIfStatTable 1 }
		
    HwIPIfStatEntry ::=
	SEQUENCE { 
		hwIpIfStatsIPVersion
	   	    INTEGER,
		hwIpIfStatsIfIndex
	   	    Integer32,				
		hwIpIfInOctetRate
	   	    Counter64,	   	    	   	    
		hwIpIfInPktRate
		    Counter64,
        hwIpIfOutOctetRate
	   	    Counter64,	   	    	   	    
		hwIpIfOutPktRate
		    Counter64,		    
		hwIpIfInOctets
		    Counter64,
		hwIpIfInPkts
		    Counter64,
		hwIpIfOutOctets
		    Counter64,
        hwIpIfOutPkts
		    Counter64		    		    		    
	         }   

    hwIpIfStatsIPVersion OBJECT-TYPE
	SYNTAX INTEGER {ipv4(1),ipv6(2)}	
	MAX-ACCESS read-only
	STATUS current
	DESCRIPTION
	    "The version of packets protocol."
			::= { hwIPIfStatEntry 1 } 


    hwIpIfStatsIfIndex OBJECT-TYPE
	SYNTAX Integer32
	MAX-ACCESS not-accessible
	STATUS current
	DESCRIPTION
  	    "Interface index(es) of port(s) present on the device ."
			::= { hwIPIfStatEntry 2 }


    hwIpIfInOctetRate OBJECT-TYPE
	SYNTAX Counter64
	MAX-ACCESS read-only
	STATUS current
	DESCRIPTION
	    "The ip rate of octets received on the interface ."
			::= { hwIPIfStatEntry 3 } 

    hwIpIfInPktRate OBJECT-TYPE
	SYNTAX Counter64
	MAX-ACCESS read-only
	STATUS current
	DESCRIPTION
	    "The ip rate of packets received on the interface ."
			::= { hwIPIfStatEntry 4 } 

    hwIpIfOutOctetRate OBJECT-TYPE
	SYNTAX Counter64
	MAX-ACCESS read-only
	STATUS current
	DESCRIPTION
	    "The ip rate of octets transmitted out of the interface ."
			::= { hwIPIfStatEntry 5 } 

    hwIpIfOutPktRate OBJECT-TYPE
	SYNTAX Counter64
	MAX-ACCESS read-only
	STATUS current
	DESCRIPTION
	    "The ip rate of packets transmitted out of the interface ."
			::= { hwIPIfStatEntry 6 }

	hwIpIfInOctets OBJECT-TYPE
	SYNTAX Counter64
	MAX-ACCESS read-only
	STATUS current
	DESCRIPTION
	    "The ip octets received on the interface ."
			::= { hwIPIfStatEntry 7 } 

    hwIpIfInPkts OBJECT-TYPE
	SYNTAX Counter64
	MAX-ACCESS read-only
	STATUS current
	DESCRIPTION
	    "The ip packets received on the interface ."
			::= { hwIPIfStatEntry 8 } 

    hwIpIfOutOctets OBJECT-TYPE
	SYNTAX Counter64
	MAX-ACCESS read-only
	STATUS current
	DESCRIPTION
	    "The ip octets transmitted out of the interface ."
			::= { hwIPIfStatEntry 9 } 

    hwIpIfOutPkts OBJECT-TYPE
	SYNTAX Counter64
	MAX-ACCESS read-only
	STATUS current
	DESCRIPTION
	    "The ip packets transmitted out of the interface ."
			::= { hwIPIfStatEntry 10 }		
	    
    hwPortDescription OBJECT IDENTIFIER ::= { hwPortMIBObjects 19 }
      
    hwPortDescriptionTable OBJECT-TYPE
	SYNTAX SEQUENCE OF HwPortDescriptionEntry
	MAX-ACCESS not-accessible
	STATUS current
	DESCRIPTION
		"This table lists the description of interfaces."
	::= { hwPortDescription 1 }
		
    hwPortDescriptionEntry OBJECT-TYPE
	SYNTAX HwPortDescriptionEntry
	MAX-ACCESS not-accessible
	STATUS current
	DESCRIPTION
    	        "This table lists the description of interfaces."
	INDEX { hwPortDescriptionIfIndex }
	::= { hwPortDescriptionTable 1 }
		
    HwPortDescriptionEntry ::=
	SEQUENCE { 
		hwPortDescriptionIfIndex
	   	    Integer32,
		hwPortDescriptionIfPortDescription
		    INTEGER
	         }   

    hwPortDescriptionIfIndex OBJECT-TYPE
	SYNTAX Integer32
	MAX-ACCESS read-only
	STATUS current
	DESCRIPTION
  	    "Interface index(es) of port(s) present on the device."
			::= { hwPortDescriptionEntry 1 }

    hwPortDescriptionIfPortDescription OBJECT-TYPE
    SYNTAX INTEGER
       { 
           router(1),
           switch(2),
           phone(3),
           desktop(4),
           null(5)
       }
    MAX-ACCESS read-write
    STATUS current
    DESCRIPTION
        "Indicates the description of ports."
            ::= { hwPortDescriptionEntry 2 }        

    hwPRBSTestInfo OBJECT IDENTIFIER ::= { hwPortMIBObjects 20 }
      
    hwPRBSTestPortStatusTable OBJECT-TYPE
    SYNTAX SEQUENCE OF HwPRBSTestPortStatusEntry
    MAX-ACCESS not-accessible
    STATUS current
    DESCRIPTION
        "This table lists the capability and result of PRBS test."
    ::= { hwPRBSTestInfo 1 }
        
    hwPRBSTestPortStatusEntry OBJECT-TYPE
    SYNTAX HwPRBSTestPortStatusEntry
    MAX-ACCESS not-accessible
    STATUS current
    DESCRIPTION
        "This table lists the capability and result of PRBS test."
    INDEX { hwPRBSTestPortStatusIfName, hwPRBSTestPortStatusSide }
    ::= { hwPRBSTestPortStatusTable 1 } 
    
    HwPRBSTestPortStatusEntry ::=
    SEQUENCE {
        hwPRBSTestPortStatusIfName
               OCTET STRING,                
        hwPRBSTestPortStatusSide
            INTEGER,
        hwPRBSTestPortStatusSuportFlag
            INTEGER,
        hwPRBSTestPortStatusPatternBitmap
            Unsigned32,
        hwPRBSTestPortStatusErrInsertLevel
            Unsigned32,
        hwPRBSTestPortStatusSlotNum
            Unsigned32,
        hwPRBSTestPortStatusCardNum
            Unsigned32,
        hwPRBSTestPortStatusPhyPortIfName
            OCTET STRING,
        hwPRBSTestPortStatusResultCount
            Unsigned32,
        hwPRBSTestPortStatusOngoingTestIndex
            Unsigned32 
        }   
          
    hwPRBSTestPortStatusIfName OBJECT-TYPE
    SYNTAX OCTET STRING (SIZE (0..64))
    MAX-ACCESS read-only
    STATUS current
    DESCRIPTION
        "Interface name of port(s) present on the device."
            ::= { hwPRBSTestPortStatusEntry 1 }

    hwPRBSTestPortStatusSide OBJECT-TYPE
    SYNTAX INTEGER {nni(0),uni(1)}
    MAX-ACCESS read-only
    STATUS current
    DESCRIPTION
        "Indicate PRBS test side."
            ::= { hwPRBSTestPortStatusEntry 2 }

    hwPRBSTestPortStatusSuportFlag OBJECT-TYPE
    SYNTAX INTEGER {notsupportinter(0),unframedandsupport(1),unframedandnotsupport(2),fractionalandsupport(3),fractionalandnotsupport(4)}
    MAX-ACCESS read-only
    STATUS current
    DESCRIPTION
        "Whether PRBS test supported."
            ::= { hwPRBSTestPortStatusEntry 3 }

    hwPRBSTestPortStatusPatternBitmap OBJECT-TYPE
    SYNTAX Unsigned32
    MAX-ACCESS read-only
    STATUS current
    DESCRIPTION
        "Indicate supported PRBS pattern by bitmap.
            bit 0  - 3   :  PRBS15,  PRBS20,  PRBS23,     QRSS, 
            bit 4  - 7   :  0S,      1S,      ALT-0-1,    1IN8, 
            bit 8  - 11  :  3IN24,   PRBS6,   PRBS9,      PRBS11, 
            bit 12       :  QRW"
            ::= { hwPRBSTestPortStatusEntry 4 }

    hwPRBSTestPortStatusErrInsertLevel OBJECT-TYPE
    SYNTAX Unsigned32
    MAX-ACCESS read-only
    STATUS current
    DESCRIPTION
        "Indicate the supported err-insert level.
            It's described by bitmap. From low to high, the different bit position indicates whether or not support 1, 1e-1, 1e-2, 1e-3, etc.
            e.g. 0x1FC (0b111111100): Range from 1e-2 to 1e-8 supported.
                 0xA (0b1010)       : Only 1e-1 and 1e-3 supported."
            ::= { hwPRBSTestPortStatusEntry 5 }

    hwPRBSTestPortStatusSlotNum OBJECT-TYPE
    SYNTAX Unsigned32
    MAX-ACCESS read-only
    STATUS current
    DESCRIPTION
        "Slot ID of the testing phyicial port."
            ::= { hwPRBSTestPortStatusEntry 6 }

    hwPRBSTestPortStatusCardNum OBJECT-TYPE
    SYNTAX Unsigned32
    MAX-ACCESS read-only
    STATUS current
    DESCRIPTION
        "Card ID of the testing phyicial port."
            ::= { hwPRBSTestPortStatusEntry 7 }

    hwPRBSTestPortStatusPhyPortIfName OBJECT-TYPE
    SYNTAX OCTET STRING (SIZE (0..64))
    MAX-ACCESS read-only
    STATUS current
    DESCRIPTION
        "Interface Name of the testing phyicial port."
            ::= { hwPRBSTestPortStatusEntry 8 }

    hwPRBSTestPortStatusResultCount OBJECT-TYPE
    SYNTAX Unsigned32
    MAX-ACCESS read-only
    STATUS current
    DESCRIPTION
        "Total count of PRBS test history result."
            ::= { hwPRBSTestPortStatusEntry 9 }

    hwPRBSTestPortStatusOngoingTestIndex OBJECT-TYPE
    SYNTAX Unsigned32
    MAX-ACCESS read-only
    STATUS current
    DESCRIPTION
        "Indicate the ongoing PRBS testing index of current interface."
            ::= { hwPRBSTestPortStatusEntry 10 }

    hwPRBSTestResultTable OBJECT-TYPE
    SYNTAX SEQUENCE OF HwPRBSTestResultEntry
    MAX-ACCESS not-accessible
    STATUS current
    DESCRIPTION
        "This table lists PRBS test result info."
    ::= { hwPRBSTestInfo 2 }
        
    hwPRBSTestResultEntry OBJECT-TYPE
    SYNTAX HwPRBSTestResultEntry
    MAX-ACCESS not-accessible
    STATUS current
    DESCRIPTION
        "This table lists PRBS test result info."
    INDEX { hwPRBSTestResultIfName, hwPRBSTestResultTestIndex }
    ::= { hwPRBSTestResultTable 1 } 
    
    HwPRBSTestResultEntry ::=
    SEQUENCE {
        hwPRBSTestResultIfName
            OCTET STRING,
        hwPRBSTestResultTestIndex
            Unsigned32,
        hwPRBSTestResultPhyPortIfName
            OCTET STRING,
        hwPRBSTestResultSide
            INTEGER,
        hwPRBSTestResultPattern
            Unsigned32,
        hwPRBSTestResultIntervalTime
            Unsigned32,
        hwPRBSTestResultIntervalCount
            Unsigned32,
        hwPRBSTestResultTestingIntervalIndex
            Unsigned32,
        hwPRBSTestResultStartTime
            DateAndTime,
        hwPRBSTestResultStopTime
            DateAndTime,
        hwPRBSTestResultProgress
            Unsigned32,
        hwPRBSTestResultRemainTime
            Unsigned32,
        hwPRBSTestResultErrInserted
            INTEGER,
        hwPRBSTestResultTotalBit
            Counter64,
        hwPRBSTestResultErrorBit
            Counter64,
        hwPRBSTestResultBerCoe
            Unsigned32,
        hwPRBSTestResultBerPow
            Unsigned32,
        hwPRBSTestResultLos
            Unsigned32,
        hwPRBSTestResultEs
            Unsigned32,
        hwPRBSTestResultEfs
            Unsigned32,
        hwPRBSTestResultSes
            Unsigned32,
        hwPRBSTestResultUas
            Unsigned32,
        hwPRBSTestResultSegmentTime
            Unsigned32,
        hwPRBSTestResultSegmentTotalCount
            Unsigned32,
        hwPRBSTestResultTestingSegmentIndex
            Unsigned32
        }   
          
    hwPRBSTestResultIfName OBJECT-TYPE
    SYNTAX OCTET STRING (SIZE (0..64))
    MAX-ACCESS read-only
    STATUS current
    DESCRIPTION
        "Interface name of port(s) present on the device."
            ::= { hwPRBSTestResultEntry 1 }

    hwPRBSTestResultTestIndex OBJECT-TYPE
    SYNTAX Unsigned32
    MAX-ACCESS read-only
    STATUS current
    DESCRIPTION
        "Indicate the PRBS test hisotry test index. 0 is invalid."
            ::= { hwPRBSTestResultEntry 2 } 

    hwPRBSTestResultPhyPortIfName OBJECT-TYPE
    SYNTAX OCTET STRING (SIZE (0..64))
    MAX-ACCESS read-only
    STATUS current
    DESCRIPTION
        "Interface Name of the testing phyicial port."
            ::= { hwPRBSTestResultEntry 3 } 

    hwPRBSTestResultSide OBJECT-TYPE
    SYNTAX INTEGER {nni(0),uni(1)}
    MAX-ACCESS read-only
    STATUS current
    DESCRIPTION
        "Indicate PRBS test side."
            ::= { hwPRBSTestResultEntry 4 } 

    hwPRBSTestResultPattern OBJECT-TYPE
    SYNTAX Unsigned32
    MAX-ACCESS read-only
    STATUS current
    DESCRIPTION
        "Indicate PRBS pattern. Refer to hwPRBSTestPortStatusPatternBitmap, but single bit here."
            ::= { hwPRBSTestResultEntry 5 } 

    hwPRBSTestResultIntervalTime OBJECT-TYPE
    SYNTAX Unsigned32
    MAX-ACCESS read-only
    STATUS current
    DESCRIPTION
        "Period time of each interval, in second."
            ::= { hwPRBSTestResultEntry 6 } 

    hwPRBSTestResultIntervalCount OBJECT-TYPE
    SYNTAX Unsigned32
    MAX-ACCESS read-only
    STATUS current
    DESCRIPTION
        "PRBS test interval repeat count."
            ::= { hwPRBSTestResultEntry 7 } 

    hwPRBSTestResultTestingIntervalIndex OBJECT-TYPE
    SYNTAX Unsigned32
    MAX-ACCESS read-only
    STATUS current
    DESCRIPTION
        "Indicate the ongoing testing interval index."
            ::= { hwPRBSTestResultEntry 8 } 

    hwPRBSTestResultStartTime OBJECT-TYPE
    SYNTAX DateAndTime
    MAX-ACCESS read-only
    STATUS current
    DESCRIPTION
        "Start time of the test."
            ::= { hwPRBSTestResultEntry 9 } 

    hwPRBSTestResultStopTime OBJECT-TYPE
    SYNTAX DateAndTime
    MAX-ACCESS read-only
    STATUS current
    DESCRIPTION
        "Stop time of the test."
            ::= { hwPRBSTestResultEntry 10 } 

    hwPRBSTestResultProgress OBJECT-TYPE
    SYNTAX Unsigned32
    MAX-ACCESS read-only
    STATUS current
    DESCRIPTION
        "Prgress of the test. 100 means 100%."
            ::= { hwPRBSTestResultEntry 11 } 

    hwPRBSTestResultRemainTime OBJECT-TYPE
    SYNTAX Unsigned32
    MAX-ACCESS read-only
    STATUS current
    DESCRIPTION
        "Remaining time of the test, in second."
            ::= { hwPRBSTestResultEntry 12 } 

    hwPRBSTestResultErrInserted OBJECT-TYPE
    SYNTAX INTEGER {yes(0),no(1)}
    MAX-ACCESS read-only
    STATUS current
    DESCRIPTION
        "Whether error-bit inserted of the test"
            ::= { hwPRBSTestResultEntry 13 } 

    hwPRBSTestResultTotalBit OBJECT-TYPE
    SYNTAX Counter64
    MAX-ACCESS read-only
    STATUS current
    DESCRIPTION
        "Total-bit of the test."
            ::= { hwPRBSTestResultEntry 14 } 

    hwPRBSTestResultErrorBit OBJECT-TYPE
    SYNTAX Counter64
    MAX-ACCESS read-only
    STATUS current
    DESCRIPTION
        "Error-bit of the test."
            ::= { hwPRBSTestResultEntry 15 } 

    hwPRBSTestResultBerCoe OBJECT-TYPE
    SYNTAX Unsigned32
    MAX-ACCESS read-only
    STATUS current
    DESCRIPTION
        "The coefficient value of bit-error-ratio."
            ::= { hwPRBSTestResultEntry 16 } 

    hwPRBSTestResultBerPow OBJECT-TYPE
    SYNTAX Unsigned32
    MAX-ACCESS read-only
    STATUS current
    DESCRIPTION
        "The power value of bit-error-ratio."
            ::= { hwPRBSTestResultEntry 17 } 

    hwPRBSTestResultLos OBJECT-TYPE
    SYNTAX Unsigned32
    MAX-ACCESS read-only
    STATUS current
    DESCRIPTION
        "Loss of sync second."
            ::= { hwPRBSTestResultEntry 18 } 

    hwPRBSTestResultEs OBJECT-TYPE
    SYNTAX Unsigned32
    MAX-ACCESS read-only
    STATUS current
    DESCRIPTION
        "Error second."
            ::= { hwPRBSTestResultEntry 19 } 

    hwPRBSTestResultEfs OBJECT-TYPE
    SYNTAX Unsigned32
    MAX-ACCESS read-only
    STATUS current
    DESCRIPTION
        "Error free second."
            ::= { hwPRBSTestResultEntry 20 } 

    hwPRBSTestResultSes OBJECT-TYPE
    SYNTAX Unsigned32
    MAX-ACCESS read-only
    STATUS current
    DESCRIPTION
        "Severely error second, comparing with 1E-3."
            ::= { hwPRBSTestResultEntry 21 } 

    hwPRBSTestResultUas OBJECT-TYPE
    SYNTAX Unsigned32
    MAX-ACCESS read-only
    STATUS current
    DESCRIPTION
        "Unavaliable seconds. Continuous severely error seconds, start counting with the 11th SES."
            ::= { hwPRBSTestResultEntry 22 } 

    hwPRBSTestResultSegmentTime OBJECT-TYPE
    SYNTAX Unsigned32
    MAX-ACCESS read-only
    STATUS current
    DESCRIPTION
        "Period time of each segment, in second."
            ::= { hwPRBSTestResultEntry 23 } 

    hwPRBSTestResultSegmentTotalCount OBJECT-TYPE
    SYNTAX Unsigned32
    MAX-ACCESS read-only
    STATUS current
    DESCRIPTION
        "Segment count of the whole PRBS test."
            ::= { hwPRBSTestResultEntry 24 } 

    hwPRBSTestResultTestingSegmentIndex OBJECT-TYPE
    SYNTAX Unsigned32
    MAX-ACCESS read-only
    STATUS current
    DESCRIPTION
        "Indicate the ongoing testing segment index."
            ::= { hwPRBSTestResultEntry 25 } 

    hwPRBSTestIntervalTable OBJECT-TYPE
    SYNTAX SEQUENCE OF HwPRBSTestIntervalEntry
    MAX-ACCESS not-accessible
    STATUS current
    DESCRIPTION
        "This table lists PRBS test interval info."
    ::= { hwPRBSTestInfo 3 }
        
    hwPRBSTestIntervalEntry OBJECT-TYPE
    SYNTAX HwPRBSTestIntervalEntry
    MAX-ACCESS not-accessible
    STATUS current
    DESCRIPTION
        "This table lists PRBS test interval info."
    INDEX { hwPRBSTestIntervalIfName, hwPRBSTestIntervalTestIndex,  hwPRBSTestIntervalIndex }
    ::= { hwPRBSTestIntervalTable 1 } 
    
    HwPRBSTestIntervalEntry ::=
    SEQUENCE {
        hwPRBSTestIntervalIfName
            OCTET STRING,
        hwPRBSTestIntervalTestIndex
            Unsigned32,
        hwPRBSTestIntervalIndex
            Unsigned32,
        hwPRBSTestIntervalStartTime
            DateAndTime,
        hwPRBSTestIntervalStopTime
            DateAndTime,
        hwPRBSTestIntervalProgress
            Unsigned32,
        hwPRBSTestIntervalRemainTime
            Unsigned32,
        hwPRBSTestIntervalErrInserted
            INTEGER,
        hwPRBSTestIntervalTotalBit
            Counter64,
        hwPRBSTestIntervalErrorBit
            Counter64,
        hwPRBSTestIntervalBerCoe
            Unsigned32,
        hwPRBSTestIntervalBerPow
            Unsigned32,
        hwPRBSTestIntervalLos
            Unsigned32,
        hwPRBSTestIntervalEs
            Unsigned32,
        hwPRBSTestIntervalEfs
            Unsigned32,
        hwPRBSTestIntervalSes
            Unsigned32,
        hwPRBSTestIntervalUas
            Unsigned32
        }   
          
    hwPRBSTestIntervalIfName OBJECT-TYPE
    SYNTAX OCTET STRING (SIZE (0..64))
    MAX-ACCESS read-only
    STATUS current
    DESCRIPTION
        "Interface name of port(s) present on the device."
            ::= { hwPRBSTestIntervalEntry 1 }

    hwPRBSTestIntervalTestIndex OBJECT-TYPE
    SYNTAX Unsigned32
    MAX-ACCESS read-only
    STATUS current
    DESCRIPTION
        "Indicate the PRBS test hisotry test index. 0 is invalid."
            ::= { hwPRBSTestIntervalEntry 2 } 

    hwPRBSTestIntervalIndex OBJECT-TYPE
    SYNTAX Unsigned32(0..60)
    MAX-ACCESS read-only
    STATUS current
    DESCRIPTION
        "Indicate the interval index of a test. 0 is invalid."
            ::= { hwPRBSTestIntervalEntry 3 } 

    hwPRBSTestIntervalStartTime OBJECT-TYPE
    SYNTAX DateAndTime
    MAX-ACCESS read-only
    STATUS current
    DESCRIPTION
        "Start time of the interval."
            ::= { hwPRBSTestIntervalEntry 4 } 

    hwPRBSTestIntervalStopTime OBJECT-TYPE
    SYNTAX DateAndTime
    MAX-ACCESS read-only
    STATUS current
    DESCRIPTION
        "Stop time of the interval"
            ::= { hwPRBSTestIntervalEntry 5 } 

    hwPRBSTestIntervalProgress OBJECT-TYPE
    SYNTAX Unsigned32
    MAX-ACCESS read-only
    STATUS current
    DESCRIPTION
        "Prgress of the interval. 100 means 100%."
            ::= { hwPRBSTestIntervalEntry 6 } 

    hwPRBSTestIntervalRemainTime OBJECT-TYPE
    SYNTAX Unsigned32
    MAX-ACCESS read-only
    STATUS current
    DESCRIPTION
        "Remaining time of the interval, in second."
            ::= { hwPRBSTestIntervalEntry 7 } 

    hwPRBSTestIntervalErrInserted OBJECT-TYPE
    SYNTAX INTEGER {yes(0),no(1)}
    MAX-ACCESS read-only
    STATUS current
    DESCRIPTION
        "Whether error-bit inserted of the interval"
            ::= { hwPRBSTestIntervalEntry 8 } 

    hwPRBSTestIntervalTotalBit OBJECT-TYPE
    SYNTAX Counter64
    MAX-ACCESS read-only
    STATUS current
    DESCRIPTION
        "Total-bit of the interval."
            ::= { hwPRBSTestIntervalEntry 9 } 

    hwPRBSTestIntervalErrorBit OBJECT-TYPE
    SYNTAX Counter64
    MAX-ACCESS read-only
    STATUS current
    DESCRIPTION
        "Error-bit of the interval."
            ::= { hwPRBSTestIntervalEntry 10 } 

    hwPRBSTestIntervalBerCoe OBJECT-TYPE
    SYNTAX Unsigned32
    MAX-ACCESS read-only
    STATUS current
    DESCRIPTION
        "The coefficient value of bit-error-ratio."
            ::= { hwPRBSTestIntervalEntry 11 } 

    hwPRBSTestIntervalBerPow OBJECT-TYPE
    SYNTAX Unsigned32
    MAX-ACCESS read-only
    STATUS current
    DESCRIPTION
        "The power value of bit-error-ratio."
            ::= { hwPRBSTestIntervalEntry 12 } 

    hwPRBSTestIntervalLos OBJECT-TYPE
    SYNTAX Unsigned32
    MAX-ACCESS read-only
    STATUS current
    DESCRIPTION
        "Loss of sync second."
            ::= { hwPRBSTestIntervalEntry 13 } 

    hwPRBSTestIntervalEs OBJECT-TYPE
    SYNTAX Unsigned32
    MAX-ACCESS read-only
    STATUS current
    DESCRIPTION
        "Error second."
            ::= { hwPRBSTestIntervalEntry 14 } 

    hwPRBSTestIntervalEfs OBJECT-TYPE
    SYNTAX Unsigned32
    MAX-ACCESS read-only
    STATUS current
    DESCRIPTION
        "Error free second."
            ::= { hwPRBSTestIntervalEntry 15 } 

    hwPRBSTestIntervalSes OBJECT-TYPE
    SYNTAX Unsigned32
    MAX-ACCESS read-only
    STATUS current
    DESCRIPTION
        "Severely error second, comparing with 1E-3."
            ::= { hwPRBSTestIntervalEntry 16 } 

    hwPRBSTestIntervalUas OBJECT-TYPE
    SYNTAX Unsigned32
    MAX-ACCESS read-only
    STATUS current
    DESCRIPTION
        "Unavaliable seconds. Continuous severely error seconds, start counting with the 11th SES."
            ::= { hwPRBSTestIntervalEntry 17 } 

    hwPRBSTestSegmentTable OBJECT-TYPE
    SYNTAX SEQUENCE OF HwPRBSTestSegmentEntry
    MAX-ACCESS not-accessible
    STATUS current
    DESCRIPTION
        "This table lists PRBS test segment info."
    ::= { hwPRBSTestInfo 4 }
        
    hwPRBSTestSegmentEntry OBJECT-TYPE
    SYNTAX HwPRBSTestSegmentEntry
    MAX-ACCESS not-accessible
    STATUS current
    DESCRIPTION
        "This table lists PRBS test segment info."
    INDEX { hwPRBSTestSegmentIfName, hwPRBSTestSegmentTestIndex, hwPRBSTestSegmentIndex }
    ::= { hwPRBSTestSegmentTable 1 } 
    
    HwPRBSTestSegmentEntry ::=
    SEQUENCE {
        hwPRBSTestSegmentIfName
            OCTET STRING,
        hwPRBSTestSegmentTestIndex
            Unsigned32,
        hwPRBSTestSegmentIndex
            Unsigned32,
        hwPRBSTestSegmentStartTime
            DateAndTime,
        hwPRBSTestSegmentEndTime
            DateAndTime,
        hwPRBSTestSegmentTotalBit
            Counter64,
        hwPRBSTestSegmentErrorBit
            Counter64,
        hwPRBSTestSegmentBerCoe
            Unsigned32,
        hwPRBSTestSegmentBerPow
            Unsigned32,
        hwPRBSTestSegmentLos
            Unsigned32,
        hwPRBSTestSegmentEs
            Unsigned32,
        hwPRBSTestSegmentEfs
            Unsigned32,
        hwPRBSTestSegmentSes
            Unsigned32,
        hwPRBSTestSegmentUas
            Unsigned32
        }   

    hwPRBSTestSegmentIfName OBJECT-TYPE
    SYNTAX OCTET STRING (SIZE (0..64))
    MAX-ACCESS read-only
    STATUS current
    DESCRIPTION
        "Interface name of port(s) present on the device."
            ::= { hwPRBSTestSegmentEntry 1 } 

    hwPRBSTestSegmentTestIndex OBJECT-TYPE
    SYNTAX Unsigned32
    MAX-ACCESS read-only
    STATUS current
    DESCRIPTION
        "Indicate the PRBS test index. 0 is invalid."
            ::= { hwPRBSTestSegmentEntry 2 } 

    hwPRBSTestSegmentIndex OBJECT-TYPE
    SYNTAX Unsigned32(0..864000)
    MAX-ACCESS read-only
    STATUS current
    DESCRIPTION
        "Indicate the segment index of a test. 0 is invalid."
            ::= { hwPRBSTestSegmentEntry 3 } 

    hwPRBSTestSegmentStartTime OBJECT-TYPE
    SYNTAX DateAndTime
    MAX-ACCESS read-only
    STATUS current
    DESCRIPTION
        "Start time of the interval."
            ::= { hwPRBSTestSegmentEntry 4 } 

    hwPRBSTestSegmentEndTime OBJECT-TYPE
    SYNTAX DateAndTime
    MAX-ACCESS read-only
    STATUS current
    DESCRIPTION
        "Stop time of the interval"
            ::= { hwPRBSTestSegmentEntry 5 } 

    hwPRBSTestSegmentTotalBit OBJECT-TYPE
    SYNTAX Counter64
    MAX-ACCESS read-only
    STATUS current
    DESCRIPTION
        "Total-bit of the segment."
            ::= { hwPRBSTestSegmentEntry 6 } 

    hwPRBSTestSegmentErrorBit OBJECT-TYPE
    SYNTAX Counter64
    MAX-ACCESS read-only
    STATUS current
    DESCRIPTION
        "Error-bit of the segment."
            ::= { hwPRBSTestSegmentEntry 7 } 

    hwPRBSTestSegmentBerCoe OBJECT-TYPE
    SYNTAX Unsigned32
    MAX-ACCESS read-only
    STATUS current
    DESCRIPTION
        "The coefficient value of bit-error-ratio."
            ::= { hwPRBSTestSegmentEntry 8 } 

    hwPRBSTestSegmentBerPow OBJECT-TYPE
    SYNTAX Unsigned32
    MAX-ACCESS read-only
    STATUS current
    DESCRIPTION
        "The power value of bit-error-ratio."
            ::= { hwPRBSTestSegmentEntry 9 } 

    hwPRBSTestSegmentLos OBJECT-TYPE
    SYNTAX Unsigned32
    MAX-ACCESS read-only
    STATUS current
    DESCRIPTION
        "Loss of sync second."
            ::= { hwPRBSTestSegmentEntry 10 } 

    hwPRBSTestSegmentEs OBJECT-TYPE
    SYNTAX Unsigned32
    MAX-ACCESS read-only
    STATUS current
    DESCRIPTION
        "Error second."
            ::= { hwPRBSTestSegmentEntry 11 } 

    hwPRBSTestSegmentEfs OBJECT-TYPE
    SYNTAX Unsigned32
    MAX-ACCESS read-only
    STATUS current
    DESCRIPTION
        "Error free second."
            ::= { hwPRBSTestSegmentEntry 12 } 

    hwPRBSTestSegmentSes OBJECT-TYPE
    SYNTAX Unsigned32
    MAX-ACCESS read-only
    STATUS current
    DESCRIPTION
        "Severely error second, comparing with 1E-3."
            ::= { hwPRBSTestSegmentEntry 13 } 

    hwPRBSTestSegmentUas OBJECT-TYPE
    SYNTAX Unsigned32
    MAX-ACCESS read-only
    STATUS current
    DESCRIPTION
        "Unavaliable seconds. Continuous severely error seconds, start counting with the 11th SES."
            ::= { hwPRBSTestSegmentEntry 14 } 

    -- 1.3.6.1.4.1.2011.5.25.157.1.21
    hwOtn OBJECT IDENTIFIER ::= { hwPortMIBObjects 21 }
	
    -- 1.3.6.1.4.1.2011.5.25.157.1.21.1
    hwOtnTable OBJECT-TYPE
        SYNTAX  SEQUENCE OF HwOtnEntry
        MAX-ACCESS not-accessible
        STATUS current
        DESCRIPTION
            "This table lists the OTN attributes of WDM interfaces."
        ::= { hwOtn 1 }
	
    -- 1.3.6.1.4.1.2011.5.25.157.1.21.1.1
    hwOtnEntry OBJECT-TYPE
        SYNTAX HwOtnEntry 
        MAX-ACCESS not-accessible
        STATUS current
        DESCRIPTION
            "This table lists the otn attributes of the WDM interface."
        INDEX { hwOtnIfIndex }
        ::= { hwOtnTable 1 }
	
    HwOtnEntry ::=
    SEQUENCE { 
        hwOtnIfIndex
            InterfaceIndex,
        hwOtnFecMode
            INTEGER,
        hwOtnFec0bitStatistics
            Counter64,
        hwOtnFec1bitStatistics
            Counter64,
        hwOtnFec0And1TypeStatistics
            Counter64,
        hwOtnFecSymbolErrStatistics
            Counter64,
        hwOtnFecUncorrectErrStatistics
            Counter64,
        hwOtnPreFecBERCoefficient
            Unsigned32,
        hwOtnPreFecBERPower
            Unsigned32,
        hwOtnAfterFecBERCoefficient
            Unsigned32,
        hwOtnAfterFecBERPower
            Unsigned32,
        hwOtnOSNR
            Integer32
    }
		 
    -- 1.3.6.1.4.1.2011.5.25.157.1.21.1.1.1
    hwOtnIfIndex OBJECT-TYPE
    SYNTAX InterfaceIndex
    MAX-ACCESS not-accessible
    STATUS current
    DESCRIPTION
        "This object indicates the interface index."
    ::= { hwOtnEntry 1 }
    
    -- 1.3.6.1.4.1.2011.5.25.157.1.21.1.1.2
    hwOtnFecMode OBJECT-TYPE
    SYNTAX INTEGER {none(0),standard(1),enhanced(2),enhancedI7(3),enhancedI4(4),lhaulsd(5)}
    MAX-ACCESS read-write
    STATUS current
    DESCRIPTION
        "This object indicates the forward error correction (FEC) mode. By default, the FEC mode is standard."
    ::= { hwOtnEntry 2 }

    -- 1.3.6.1.4.1.2011.5.25.157.1.21.1.1.3
    hwOtnFec0bitStatistics OBJECT-TYPE
        SYNTAX Counter64
        MAX-ACCESS read-only
        STATUS current
        DESCRIPTION
            "This object indicates the number of 0 bits corrected by FEC."  
        ::= { hwOtnEntry 3 }

    -- 1.3.6.1.4.1.2011.5.25.157.1.21.1.1.4
    hwOtnFec1bitStatistics OBJECT-TYPE
        SYNTAX Counter64
        MAX-ACCESS read-only
        STATUS current
        DESCRIPTION
            "This object indicates the number of 1 bits corrected by FEC."  
        ::= { hwOtnEntry 4 }

    -- 1.3.6.1.4.1.2011.5.25.157.1.21.1.1.5
    hwOtnFec0And1TypeStatistics OBJECT-TYPE
        SYNTAX Counter64
        MAX-ACCESS read-only
        STATUS current
        DESCRIPTION
            "This object indicates the number of 0 bits and the number of 1 bits corrected by FEC."  
        ::= { hwOtnEntry 5 }

    -- 1.3.6.1.4.1.2011.5.25.157.1.21.1.1.6
    hwOtnFecSymbolErrStatistics OBJECT-TYPE
        SYNTAX Counter64
        MAX-ACCESS read-only
        STATUS current
        DESCRIPTION
            "This object indicates the number of bytes corrected by FEC."  
        ::= { hwOtnEntry 6 }

    -- 1.3.6.1.4.1.2011.5.25.157.1.21.1.1.7
    hwOtnFecUncorrectErrStatistics OBJECT-TYPE
        SYNTAX Counter64
        MAX-ACCESS read-only
        STATUS current
        DESCRIPTION
            "This object indicates the number of blocks that cannot be corrected by FEC."  
        ::= { hwOtnEntry 7 }

    -- 1.3.6.1.4.1.2011.5.25.157.1.21.1.1.8
    hwOtnPreFecBERCoefficient OBJECT-TYPE
        SYNTAX Unsigned32
        MAX-ACCESS read-only
        STATUS current
        DESCRIPTION
            "This object indicates the coefficient for bit error statistics before FEC."  
        ::= { hwOtnEntry 8 }

    -- 1.3.6.1.4.1.2011.5.25.157.1.21.1.1.9
    hwOtnPreFecBERPower OBJECT-TYPE
        SYNTAX Unsigned32
        MAX-ACCESS read-only
        STATUS current
        DESCRIPTION
            "This object indicates the power for bit error statistics before FEC."  
        ::= { hwOtnEntry 9 }

    -- 1.3.6.1.4.1.2011.5.25.157.1.21.1.1.10
    hwOtnAfterFecBERCoefficient OBJECT-TYPE
        SYNTAX Unsigned32
        MAX-ACCESS read-only
        STATUS current
        DESCRIPTION
           "This object indicates the coefficient for bit error statistics after FEC."  
        ::= { hwOtnEntry 10 }

    -- 1.3.6.1.4.1.2011.5.25.157.1.21.1.1.11
    hwOtnAfterFecBERPower OBJECT-TYPE
        SYNTAX Unsigned32
        MAX-ACCESS read-only
        STATUS current
        DESCRIPTION
            "This object indicates the power for bit error statistics after FEC."  
        ::= { hwOtnEntry 11 }

    -- 1.3.6.1.4.1.2011.5.25.157.1.21.1.1.14
    hwOtnOSNR OBJECT-TYPE
        SYNTAX Integer32
        MAX-ACCESS read-only
        STATUS current
        DESCRIPTION
            "This object indicates the optical signal-to-noise ratio."  
        ::= { hwOtnEntry 14 }
	
    hwLogicalPort OBJECT IDENTIFIER ::= { hwPortMIBObjects 22 }
    
    hwLogicalPortTable OBJECT-TYPE
	SYNTAX SEQUENCE OF HwLogicalPortEntry
	MAX-ACCESS not-accessible
	STATUS current
	DESCRIPTION
	    "This table lists the working status of the logical ports."
	::= { hwLogicalPort 1 }

    hwLogicalPortEntry OBJECT-TYPE
	SYNTAX HwLogicalPortEntry
	MAX-ACCESS not-accessible
	STATUS current
	DESCRIPTION
    	    "This table lists the working status of the logical ports."
	INDEX { hwLogicalPortIfIndex }
	::= { hwLogicalPortTable 1 }

    HwLogicalPortEntry ::=
	SEQUENCE { 
		hwLogicalPortIfIndex
	   	    InterfaceIndex,
		hwLogicalPortStatisticEnable
		    INTEGER
	                        }   

    hwLogicalPortIfIndex OBJECT-TYPE
	SYNTAX InterfaceIndex
	MAX-ACCESS read-only
	STATUS current
	DESCRIPTION
  	    "Interface index(es) of the logical port(s) present on the device ."
        ::= { hwLogicalPortEntry 1 }

    hwLogicalPortStatisticEnable OBJECT-TYPE
        SYNTAX INTEGER { neither(1), inbound(2), outbound(3), both(4) }
        MAX-ACCESS read-write
        STATUS current
        DESCRIPTION
            "Indicates the statistic enable status of the logical port(s) ."
        ::= { hwLogicalPortEntry 2 }
	
		-- 1.3.6.1.4.1.2011.5.25.157.1.23
		hwNarrowBand OBJECT IDENTIFIER ::= { hwPortMIBObjects 23 }

		
		-- 1.3.6.1.4.1.2011.5.25.157.1.23.1
		hwEmTable OBJECT-TYPE
			SYNTAX SEQUENCE OF HwEmEntry
			MAX-ACCESS not-accessible
			STATUS current
			DESCRIPTION
				"This table lists the attributes of all E&M interfaces."
			::= { hwNarrowBand 1 }

		
		-- 1.3.6.1.4.1.2011.5.25.157.1.23.1.1
		hwEmEntry OBJECT-TYPE
			SYNTAX HwEmEntry
			MAX-ACCESS not-accessible
			STATUS current
			DESCRIPTION
				"This table lists the attributes of all E&M interfaces."
			INDEX { hwEmIfIndex }
			::= { hwEmTable 1 }

		
		HwEmEntry ::=
			SEQUENCE { 
				hwEmIfIndex
					InterfaceIndex,
				hwEmPcmMode
					INTEGER,
				hwEmSignalMode
					INTEGER,
				hwEmReceiveGain
					OCTET STRING,
				hwEmSendGain
					OCTET STRING,
				hwEmUserLine
					INTEGER
			 }

		-- 1.3.6.1.4.1.2011.5.25.157.1.23.1.1.1
		hwEmIfIndex OBJECT-TYPE
			SYNTAX InterfaceIndex
			MAX-ACCESS not-accessible
			STATUS current
			DESCRIPTION
				"The value of this object identifies the index of an E&M interface."
			::= { hwEmEntry 1 }

		
		-- 1.3.6.1.4.1.2011.5.25.157.1.23.1.1.2
		hwEmPcmMode OBJECT-TYPE
			SYNTAX INTEGER
				{
				aLaw(1),
				uLaw(2)
				}
			MAX-ACCESS read-write
			STATUS current
			DESCRIPTION
				"This object indicates the PCM mode of an E&M interface. 
				The value can be A-Law or U-Law. The default value is A-Law."
			::= { hwEmEntry 2 }

		
		-- 1.3.6.1.4.1.2011.5.25.157.1.23.1.1.3
		hwEmSignalMode OBJECT-TYPE
			SYNTAX INTEGER
				{
				bell1(1),
				bell2(2),
				bell3(3),
				bell4(4),
				bell5(5)
				}
			MAX-ACCESS read-write
			STATUS current
			DESCRIPTION
				"This object indicates the signaling mode of an E&M interface.
				The value can be Bell-1,Bell-2,Bell-3,Bell-4 or Bell-5. The default value is Bell-5."
			::= { hwEmEntry 3 }

		
		-- 1.3.6.1.4.1.2011.5.25.157.1.23.1.1.4
		hwEmReceiveGain OBJECT-TYPE
			SYNTAX OCTET STRING
			MAX-ACCESS read-write
			STATUS current
			DESCRIPTION
				"This object indicates the receive gain of an E&M interface. 
				The value ranges from -20 to 1.5 with a step of 0.5, in dB. 
				The default value is 0 dB."
			::= { hwEmEntry 4 }

		
		-- 1.3.6.1.4.1.2011.5.25.157.1.23.1.1.5
		hwEmSendGain OBJECT-TYPE
			SYNTAX OCTET STRING
			MAX-ACCESS read-write
			STATUS current
			DESCRIPTION
				"This object indicates the transmit gain of an E&M interface. 
				The value ranges from -7 to 13.5 with a step of 0.5, in dB. 
				The default value is 0 dB.
				"
			::= { hwEmEntry 5 }

		
		-- 1.3.6.1.4.1.2011.5.25.157.1.23.1.1.6
		hwEmUserLine OBJECT-TYPE
			SYNTAX INTEGER
				{
				twoWire(1),
				fourWire(2)
				}
			MAX-ACCESS read-write
			STATUS current
			DESCRIPTION
				"This object indicates the user line mode of an E&M interface. 
				The value can be 2-wire or 4-wire. 
				The default value is 4-wire.
				"
			::= { hwEmEntry 6 }

		
		-- 1.3.6.1.4.1.2011.5.25.157.1.23.2
		hwFxsoTable OBJECT-TYPE
			SYNTAX SEQUENCE OF HwFxsoEntry
			MAX-ACCESS not-accessible
			STATUS current
			DESCRIPTION
				"This table lists the attributes of all FXS/FXO interfaces."
			::= { hwNarrowBand 2 }

		
		-- 1.3.6.1.4.1.2011.5.25.157.1.23.2.1
		hwFxsoEntry OBJECT-TYPE
			SYNTAX HwFxsoEntry
			MAX-ACCESS not-accessible
			STATUS current
			DESCRIPTION
				"This table lists the attributes of all FXS/FXO interfaces."
			INDEX { hwEmIfIndex }
			::= { hwFxsoTable 1 }

		
		HwFxsoEntry ::=
			SEQUENCE { 
				hwFxsoIfIndex
					InterfaceIndex,
				hwFxsoPortMode
					INTEGER,
				hwFxsoPcmMode
					INTEGER,
				hwFxsCurrent
					INTEGER,
				hwFxsImpedance
					Integer32,
				hwFxsReceiveGain
					OCTET STRING,
				hwFxsSendGain
					OCTET STRING,
				hwFxsLineLock
					INTEGER,
				hwFxsHotLine
					INTEGER,
				hwFxoFeedMaxVoltage
					Integer32,
				hwFxoFeedMinVoltage
					Integer32,
				hwFxoFeedMaxCurrent
					INTEGER,
				hwFxoFeedMinCurrent
					INTEGER,
				hwFxoReceiveGain
					OCTET STRING,
				hwFxoSendGain
					OCTET STRING,
				hwFxoDcImpedance
					INTEGER,
				hwFxoAcImpedance
					Integer32,
				hwFxoRingMinDuration
					INTEGER,
				hwFxoRingMaxInterval
					INTEGER,
				hwFxoRingFrequence
					INTEGER,
				hwFxoRingAcAmplitude
					INTEGER,
				hwFxoRingOffset
					Integer32
			 }

		-- 1.3.6.1.4.1.2011.5.25.157.1.23.2.1.1
		hwFxsoIfIndex OBJECT-TYPE
			SYNTAX InterfaceIndex
			MAX-ACCESS not-accessible
			STATUS current
			DESCRIPTION
				"The value of this object identifies the index of an FXS/FXO."
			::= { hwFxsoEntry 1 }

		
		-- 1.3.6.1.4.1.2011.5.25.157.1.23.2.1.2
		hwFxsoPortMode OBJECT-TYPE
			SYNTAX INTEGER
				{
				fxs(7),
				fxo(8)
				}
			MAX-ACCESS read-write
			STATUS current
			DESCRIPTION
				"This object indicates the type of an FXS/FXO interface.
				For NED1MPAA/CR23MPAA PICs, the last four ports (ports 6, 7, 8, and 9) can work either in fxo or fxs mode. 
				The default mode is fxo.
				"
			::= { hwFxsoEntry 2 }

		
		-- 1.3.6.1.4.1.2011.5.25.157.1.23.2.1.3
		hwFxsoPcmMode OBJECT-TYPE
			SYNTAX INTEGER
				{
				aLaw(1),
				uLaw(2)
				}
			MAX-ACCESS read-write
			STATUS current
			DESCRIPTION
				"This object indicates the PCM mode of an FXS/FXO interface.
				The value can be A-Law or U-Law. The default value is A-Law."
			::= { hwFxsoEntry 3 }

		
		-- 1.3.6.1.4.1.2011.5.25.157.1.23.2.1.4
		hwFxsCurrent OBJECT-TYPE
			SYNTAX INTEGER
				{
				mA16(1),
				mA20(2)
				}
			MAX-ACCESS read-write
			STATUS current
			DESCRIPTION
				"This object indicates the current of an FXS interface.
				The value can be 16mA or 20mA. The default value is 16mA.
				"
			::= { hwFxsoEntry 4 }

		
		-- 1.3.6.1.4.1.2011.5.25.157.1.23.2.1.5
		hwFxsImpedance OBJECT-TYPE
			SYNTAX Integer32 (0..15)
			MAX-ACCESS read-write
			STATUS current
			DESCRIPTION
				"This object indicates the impedance of an FXS interface.The value can be:		
				value 0: 600 ohm
				value 1: 900 ohm
				value 2: 270 ohm + (750 ohm || 150 nF) and 275 ohm + (780 ohm || 150 nF)
				value 3: 220 ohm + (820 ohm || 120 nF) and 220 ohm + (820 ohm || 115 nF)
				value 4: 370 ohm + (620 ohm || 310 nF)
				value 5: 320 ohm + (1050 ohm || 230 nF)
				value 6: 370 ohm + (820 ohm || 110 nF)
				value 7: 275 ohm + (780 ohm || 115 nF)
				value 8: 20 ohm + (820 ohm || 110 nF)
				value 9: 350 ohm + (1000 ohm || 210 nF)
				value 10:200 ohm + (680 ohm || 100 nF)
				value 11:600 ohm + 2.16 uF
				value 12:900 ohm + 1 uF
				value 13:900 ohm + 2.16 uF
				value 14:600 ohm + 1 uF
				value 15: Global impedance
				The default value is 600 ohm."
			::= { hwFxsoEntry 5 }

		
		-- 1.3.6.1.4.1.2011.5.25.157.1.23.2.1.6
		hwFxsReceiveGain OBJECT-TYPE
			SYNTAX OCTET STRING
			MAX-ACCESS read-write
			STATUS current
			DESCRIPTION
				"This object indicates the receive gain of an FXS interface. 
				The value ranges from -12 to 0 with a step of 0.5, in dB. 
				The default value is -7 dB.
				"
			::= { hwFxsoEntry 6 }

		
		-- 1.3.6.1.4.1.2011.5.25.157.1.23.2.1.7
		hwFxsSendGain OBJECT-TYPE
			SYNTAX OCTET STRING
			MAX-ACCESS read-write
			STATUS current
			DESCRIPTION
				"This object indicates the transmit gain of an FXS interface. 
				The value ranges from -6 to 5 with a step of 0.5, in dB. 
				The default value is 0 dB.
				"
			::= { hwFxsoEntry 7 }

		
		-- 1.3.6.1.4.1.2011.5.25.157.1.23.2.1.8
		hwFxsLineLock OBJECT-TYPE
			SYNTAX INTEGER
				{
				enable(1),
				disable(2)
				}
			MAX-ACCESS read-write
			STATUS current
			DESCRIPTION
				"This object indicates whether line lock is enabled for an FXS interface.
				The value can be enable or disable. The default value is enable."
			::= { hwFxsoEntry 8 }

		
		-- 1.3.6.1.4.1.2011.5.25.157.1.23.2.1.9
		hwFxsHotLine OBJECT-TYPE
			SYNTAX INTEGER
				{
				enable(1),
				disable(2)
				}
			MAX-ACCESS read-write
			STATUS current
			DESCRIPTION
				"
				This object indicates whether the hotline function is enabled for an FXS interface.
				The value can be enable or disable. The default value is enable."
			::= { hwFxsoEntry 9 }

		
		-- 1.3.6.1.4.1.2011.5.25.157.1.23.2.1.10
		hwFxoFeedMaxVoltage OBJECT-TYPE
			SYNTAX Integer32 (-100..0)
			MAX-ACCESS read-write
			STATUS current
			DESCRIPTION
				"This object indicates the maximum feed voltage allowed by an FXO interface.
				The value ranges from -100 to 0. The default value is -20V."
			::= { hwFxsoEntry 10 }

		
		-- 1.3.6.1.4.1.2011.5.25.157.1.23.2.1.11
		hwFxoFeedMinVoltage OBJECT-TYPE
			SYNTAX Integer32 (-100..0)
			MAX-ACCESS read-write
			STATUS current
			DESCRIPTION
				"This object indicates the minimum feed voltage allowed by an FXO interface.
				The value ranges from -100 to 0. The default value is -80V."
			::= { hwFxsoEntry 11 }

		
		-- 1.3.6.1.4.1.2011.5.25.157.1.23.2.1.12
		hwFxoFeedMaxCurrent OBJECT-TYPE
			SYNTAX INTEGER
				{
				mA25(1),
				mA30(2),
				mA35(3),
				mA40(4)
				}
			MAX-ACCESS read-write
			STATUS current
			DESCRIPTION
				"This object indicates the maximum feed current allowed by an FXO interface.
				The value can be 25mA,30mA,35mA or 40mA. The default value is 35mA."
			::= { hwFxsoEntry 12 }

		
		-- 1.3.6.1.4.1.2011.5.25.157.1.23.2.1.13
		hwFxoFeedMinCurrent OBJECT-TYPE
			SYNTAX INTEGER
				{
				mA16(1),
				mA17(2),
				mA18(3),
				mA19(4),
				mA20(5)
				}
			MAX-ACCESS read-write
			STATUS current
			DESCRIPTION
				"This object indicates the minimum feed current allowed by an FXO interface.
				The value can be 16mA,17mA,18mA,19mA or 20mA. The default value is 16mA."
			::= { hwFxsoEntry 13 }

		
		-- 1.3.6.1.4.1.2011.5.25.157.1.23.2.1.14
		hwFxoReceiveGain OBJECT-TYPE
			SYNTAX OCTET STRING
			MAX-ACCESS read-write
			STATUS current
			DESCRIPTION
				"This object indicates the receive gain of an FXO interface.
				The value ranges from -6 to 5 with a step of 0.5, in dB. 
				The default value is 0 dB."
			::= { hwFxsoEntry 14 }

		
		-- 1.3.6.1.4.1.2011.5.25.157.1.23.2.1.15
		hwFxoSendGain OBJECT-TYPE
			SYNTAX OCTET STRING
			MAX-ACCESS read-write
			STATUS current
			DESCRIPTION
				"This object indicates the transmit gain of an FXO interface.
				The value ranges from -6 to 5 with a step of 0.5, in dB. 
				The default value is 0 dB."
			::= { hwFxsoEntry 15 }

		
		-- 1.3.6.1.4.1.2011.5.25.157.1.23.2.1.16
		hwFxoDcImpedance OBJECT-TYPE
			SYNTAX INTEGER
				{
				ohm50(1),
				ohm800(2)
				}
			MAX-ACCESS read-write
			STATUS current
			DESCRIPTION
				"This object indicates the DC impedance of an FXO interface.
				The value can be 50 ohm or 800 ohm. The default value is 50 ohm.
				"
			::= { hwFxsoEntry 16 }

		
		-- 1.3.6.1.4.1.2011.5.25.157.1.23.2.1.17
		hwFxoAcImpedance OBJECT-TYPE
			SYNTAX Integer32 (0..15)
			MAX-ACCESS read-write
			STATUS current
			DESCRIPTION
				"This object indicates the AC impedance of an FXO interface.The value can be:		
				value 0: 600 ohm
				value 1: 900 ohm
				value 2: 270 ohm + (750 ohm || 150 nF) and 275 ohm + (780 ohm || 150 nF)
				value 3: 220 ohm + (820 ohm || 120 nF) and 220 ohm + (820 ohm || 115 nF)
				value 4: 370 ohm + (620 ohm || 310 nF)
				value 5: 320 ohm + (1050 ohm || 230 nF)
				value 6: 370 ohm + (820 ohm || 110 nF)
				value 7: 275 ohm + (780 ohm || 115 nF)
				value 8: 20 ohm + (820 ohm || 110 nF)
				value 9: 350 ohm + (1000 ohm || 210 nF)
				value 10:200 ohm + (680 ohm || 100 nF)
				value 11:600 ohm + 2.16 uF
				value 12:900 ohm + 1 uF
				value 13:900 ohm + 2.16 uF
				value 14:600 ohm + 1 uF
				value 15: Global impedance
				The default value is 600 ohm."
			::= { hwFxsoEntry 17 }

		
		-- 1.3.6.1.4.1.2011.5.25.157.1.23.2.1.18
		hwFxoRingMinDuration OBJECT-TYPE
			SYNTAX INTEGER
				{
				ms100(1),
				ms150(2),
				ms200(3),
				ms256(4),
				ms384(5),
				ms512(6),
				ms640(7),
				ms1024(8)
				}
			MAX-ACCESS read-write
			STATUS current
			DESCRIPTION
				"This object indicates the minimum duration that an FXO interface takes to confirm a ringing current.
				The value can be 100ms,150ms,200ms,256ms,384ms,512ms,640ms or 1024ms. The default value is 200ms."
			::= { hwFxsoEntry 18 }

		
		-- 1.3.6.1.4.1.2011.5.25.157.1.23.2.1.19
		hwFxoRingMaxInterval OBJECT-TYPE
			SYNTAX INTEGER
				{
				notuse(1),
				ms128(2),
				ms256(3),
				ms284(4),
				ms512(5),
				ms640(6),
				ms768(7),
				ms896(8),
				ms1024(9),
				ms1152(10),
				ms1280(11),
				ms1408(12),
				ms1536(13),
				ms1664(14),
				ms1792(15),
				ms1920(16)
				}
			MAX-ACCESS read-write
			STATUS current
			DESCRIPTION
				"This object indicates a ringing current timeout period on a FXO interface.
				The default value is notuse.
				"
			::= { hwFxsoEntry 19 }

		
		-- 1.3.6.1.4.1.2011.5.25.157.1.23.2.1.20
		hwFxoRingFrequence OBJECT-TYPE
			SYNTAX INTEGER
				{
				hz16(1),
				hz25(2),
				hz50(3)
				}
			MAX-ACCESS read-write
			STATUS current
			DESCRIPTION
				"This object indicates a ringing current's frequency detected by an FXO interface.
				The value can be 16hz,25hz or 50hz. The default value is 25hz."
			::= { hwFxsoEntry 20 }

		
		-- 1.3.6.1.4.1.2011.5.25.157.1.23.2.1.21
		hwFxoRingAcAmplitude OBJECT-TYPE
			SYNTAX INTEGER
				{
				v74(1),
				v65(2),
				v50(3)
				}
			MAX-ACCESS read-write
			STATUS current
			DESCRIPTION
				"This object indicates a ringing current's AC amplitude detected by an FXO interface.
				The value can be 74V,65V or 50V. The default value is 50V.
				"
			::= { hwFxsoEntry 21 }

		
		-- 1.3.6.1.4.1.2011.5.25.157.1.23.2.1.22
		hwFxoRingOffset OBJECT-TYPE
			SYNTAX Integer32 (0..100)
			MAX-ACCESS read-write
			STATUS current
			DESCRIPTION
				"This object indicates a ringing current's AC offset detected by an FXO interface.
				The value ranges from 0 to 100. The default value is 70mA."
			::= { hwFxsoEntry 22 }

		
		-- 1.3.6.1.4.1.2011.5.25.157.1.23.3
		hwRsTable OBJECT-TYPE
			SYNTAX SEQUENCE OF HwRsEntry
			MAX-ACCESS not-accessible
			STATUS current
			DESCRIPTION
				"This table lists the attributes of all RS interfaces."
			::= { hwNarrowBand 3 }

		
		-- 1.3.6.1.4.1.2011.5.25.157.1.23.3.1
		hwRsEntry OBJECT-TYPE
			SYNTAX HwRsEntry
			MAX-ACCESS not-accessible
			STATUS current
			DESCRIPTION
				"This table lists the attributes of all RS interfaces."
			INDEX { hwEmIfIndex }
			::= { hwRsTable 1 }

		
		HwRsEntry ::=
			SEQUENCE { 
				hwRsIfIndex
					InterfaceIndex,
				hwRsPortMode
					INTEGER,
				hwRsWorkMode
					INTEGER,
				hwRsPhysicalMode
					INTEGER,
				hwRsClockSource
					INTEGER,
				hwRsBaudrate
					Integer32,
				hwRsClockSendMode
					INTEGER,
				hwRsClockReceiveMode
					INTEGER,
				hwRsParity
					INTEGER,
				hwRsStopbits
					INTEGER,
				hwRsDatabits
					Integer32,
				hwRsMuxProtocol
					INTEGER,
				hwRsX50PhaseMode
					INTEGER
			 }

		-- 1.3.6.1.4.1.2011.5.25.157.1.23.3.1.1
		hwRsIfIndex OBJECT-TYPE
			SYNTAX InterfaceIndex
			MAX-ACCESS not-accessible
			STATUS current
			DESCRIPTION
				"The value of this object identifies the index of a serial interface on a device.
				"
			::= { hwRsEntry 1 }

		
		-- 1.3.6.1.4.1.2011.5.25.157.1.23.3.1.2
		hwRsPortMode OBJECT-TYPE
			SYNTAX INTEGER
				{
				rs232(1),
				rs485(2),
				rs422(3),
				v24(4),
				x21(5),
				v35(6)
				}
			MAX-ACCESS read-write
			STATUS current
			DESCRIPTION
				"This object indicates the type of a serial interface.
				The value can be rs-232,rs-485,rs-422,,v.24,x.21 or v.35.
				For  NED1MPAA/CR23MPAA PICs: 
				Ports 0 and 2 work in rs-232 mode. The working mode cannot be configured.
				Ports 1 and 3 can work either in rs-485 or rs-422 mode. The default mode is rs-422.
				For  NED1SA8/CR23SA8 PICs, all ports can work in v-35, x-21, or v-24 mode. The default mode is v-24.
				"
			::= { hwRsEntry 2 }

		
		-- 1.3.6.1.4.1.2011.5.25.157.1.23.3.1.3
		hwRsWorkMode OBJECT-TYPE
			SYNTAX INTEGER
				{
				dce(1),
				dte(2)
				}
			MAX-ACCESS read-write
			STATUS current
			DESCRIPTION
				"This object indicates the mode in which a serial interface works.
				The value can be dce or dte. The default value is dce."
			::= { hwRsEntry 3 }

		
		-- 1.3.6.1.4.1.2011.5.25.157.1.23.3.1.4
		hwRsPhysicalMode OBJECT-TYPE
			SYNTAX INTEGER
				{
				async(1),
				sync(2)
				}
			MAX-ACCESS read-write
			STATUS current
			DESCRIPTION
				"This object indicates the mode in which a serial interface transmits signals.
				The value can be async or sync. The default value is async."
			::= { hwRsEntry 4 }

		
		-- 1.3.6.1.4.1.2011.5.25.157.1.23.3.1.5
		hwRsClockSource OBJECT-TYPE
			SYNTAX INTEGER
				{
				internal(1),
				external(2),
				slave(3)
				}
			MAX-ACCESS read-write
			STATUS current
			DESCRIPTION
				"This object indicates the clock source mode of a serial interface.
				The value can be internal,external or slave. The default value is internal."
			::= { hwRsEntry 5 }

		
		-- 1.3.6.1.4.1.2011.5.25.157.1.23.3.1.6
		hwRsBaudrate OBJECT-TYPE
			SYNTAX Integer32 (0..38)
			MAX-ACCESS read-write
			STATUS current
			DESCRIPTION
				"This object indicates the baud rate of a serial interface.
				The value can be :
				0: 600bit/s, 1: 1200bit/s, 2: 2400bit/s, 3: 4800bit/s,                                                      
				4: 9600bit/s, 5: 19200bit/s, 6: 38400bit/s, 7: 48000bit/s, 8~38: N*64Kbit/s N<=31. 
				The default value is 9600 bit/s in asynchronous transmission mode 
				and 64 kbit/s in synchronous transmission mode."
				
			::= { hwRsEntry 6 }

		
		-- 1.3.6.1.4.1.2011.5.25.157.1.23.3.1.7
		hwRsClockSendMode OBJECT-TYPE
			SYNTAX INTEGER
				{
				inphase(1),
				inversephase(2)
				}
			MAX-ACCESS read-write
			STATUS current
			DESCRIPTION
				"This object indicates the mode in which clock signals transmitted by a serial interface are sampled. 
				This mode can be configured in synchronous clock mode.
				The value can be inphase or inversephase. The default value is inversephase."
			::= { hwRsEntry 7 }

		
		-- 1.3.6.1.4.1.2011.5.25.157.1.23.3.1.8
		hwRsClockReceiveMode OBJECT-TYPE
			SYNTAX INTEGER
				{
				inphase(1),
				inversephase(2)
				}
			MAX-ACCESS read-write
			STATUS current
			DESCRIPTION
				"This object indicates the mode in which clock signals received by a serial interface are sampled. 
				This mode can be configured in synchronous clock mode.
				The value can be inphase or inversephase. The default value is inphase."
			::= { hwRsEntry 8 }

		
		-- 1.3.6.1.4.1.2011.5.25.157.1.23.3.1.9
		hwRsParity OBJECT-TYPE
			SYNTAX INTEGER
				{
				none(1),
				even(2),
				odd(3)
				}
			MAX-ACCESS read-write
			STATUS current
			DESCRIPTION
				"This object indicates the parity check mode of a serial interface's asynchronous frames. 
				This mode can be configured in asynchronous clock mode.
				The value can be none,even or odd. The default value is none."
			::= { hwRsEntry 9 }

		
		-- 1.3.6.1.4.1.2011.5.25.157.1.23.3.1.10
		hwRsStopbits OBJECT-TYPE
			SYNTAX INTEGER
				{
				bits1(1),
				bits2(2)
				}
			MAX-ACCESS read-write
			STATUS current
			DESCRIPTION
				"This object indicates the number of stop bits contained in a serial interface's asynchronous frame. 
				This object can be configured in asynchronous clock mode.
				The value can be 1-bits or 2-bits. The default value is 1-bits."
			::= { hwRsEntry 10 }

		
		-- 1.3.6.1.4.1.2011.5.25.157.1.23.3.1.11
		hwRsDatabits OBJECT-TYPE
			SYNTAX Integer32 (5..8)
			MAX-ACCESS read-write
			STATUS current
			DESCRIPTION
				"This object indicates the number of data bits contained in a serial interface's asynchronous frame.
				This object can be configured in asynchronous clock mode.
				The value ranges from 5 to 8 bits.The default value is 8 bits."
			::= { hwRsEntry 11 }

		
		-- 1.3.6.1.4.1.2011.5.25.157.1.23.3.1.12
		hwRsMuxProtocol OBJECT-TYPE
			SYNTAX INTEGER
				{
				sbitloop(1),
				sbit0(2),
				sbit1(3)
				}
			MAX-ACCESS read-write
			STATUS current
			DESCRIPTION
				"This object indicates the type of a serial interface's sub-rate multiplexing protocol. 
				This object can be configured in asynchronous clock mode.
				The value can be sbit-loop,sbit=0 or sbit=1. The default value is sbit-loop."
			::= { hwRsEntry 12 }

		
		-- 1.3.6.1.4.1.2011.5.25.157.1.23.3.1.13
		hwRsX50PhaseMode OBJECT-TYPE
			SYNTAX INTEGER
				{
				sequence(1),
				interval(2)
				}
			MAX-ACCESS read-write
			STATUS current
			DESCRIPTION
				"This object indicates the envelope phase mode multiplexed by a serial interface's x.50 sub-rate.
				The value can be sequence or interval. The default value is sequence.
				"
			::= { hwRsEntry 13 }

		
		-- 1.3.6.1.4.1.2011.5.25.157.1.23.4
		hwGlobalCfgTable OBJECT-TYPE
			SYNTAX SEQUENCE OF HwGlobalCfgEntry
			MAX-ACCESS not-accessible
			STATUS current
			DESCRIPTION
				"This table lists the global physical attributes of all narrowband interfaces."
			::= { hwNarrowBand 4 }

		
		-- 1.3.6.1.4.1.2011.5.25.157.1.23.4.1
		hwGlobalCfgEntry OBJECT-TYPE
			SYNTAX HwGlobalCfgEntry
			MAX-ACCESS not-accessible
			STATUS current
			DESCRIPTION
				"This table lists the global physical attributes of all narrowband interfaces."
			INDEX { hwEmIfIndex }
			::= { hwGlobalCfgTable 1 }

		
		HwGlobalCfgEntry ::=
			SEQUENCE { 
				hwNarrowBandCardId
					Integer32,
				hwSignalMode
					INTEGER,
				hwUserLine
					INTEGER
			 }

		-- 1.3.6.1.4.1.2011.5.25.157.1.23.4.1.1
		hwNarrowBandCardId OBJECT-TYPE
			SYNTAX Integer32
			MAX-ACCESS read-only
			STATUS current
			DESCRIPTION
				"The value of this object identifies the ID of a narrowband card on a device."
			::= { hwGlobalCfgEntry 1 }

		
		-- 1.3.6.1.4.1.2011.5.25.157.1.23.4.1.2
		hwSignalMode OBJECT-TYPE
			SYNTAX INTEGER
				{
				bell1(1),
				bell2(2),
				bell3(3),
				bell4(4),
				bell5(5)
				}
			MAX-ACCESS read-write
			STATUS current
			DESCRIPTION
				"Indicates the global signal mode of the physical serial interface.
				By default, the signal mode is bell5.
				This object indicates the global signaling mode of an E&M interface.
				The value can be Bell-1,Bell-2,Bell-3,Bell-4 or Bell-5. The default value is Bell-5."
			::= { hwGlobalCfgEntry 2 }

		
		-- 1.3.6.1.4.1.2011.5.25.157.1.23.4.1.3
		hwUserLine OBJECT-TYPE
			SYNTAX INTEGER
				{
				twoWire(1),
				fourWire(2)
				}
			MAX-ACCESS read-write
			STATUS current
			DESCRIPTION
				"This object indicates the global user line mode of an E&M interface.
				The value can be 2-wire or 4-wire. The default value is 4-wire."
			::= { hwGlobalCfgEntry 3 }
		-- 1.3.6.1.4.1.2011.5.25.157.1.23.5
		hwNbCommonTable OBJECT-TYPE
			SYNTAX SEQUENCE OF HwNbCommonEntry
			MAX-ACCESS not-accessible
			STATUS current
			DESCRIPTION
				"This table lists the common attributes of all narrowband interfaces."
			::= { hwNarrowBand 5 }

		
		-- 1.3.6.1.4.1.2011.5.25.157.1.23.5.1
		hwNbCommonEntry OBJECT-TYPE
			SYNTAX HwNbCommonEntry
			MAX-ACCESS not-accessible
			STATUS current
			DESCRIPTION
				"This table lists the common attributes of all narrowband interfaces."
			INDEX { hwEmIfIndex }
			::= { hwNbCommonTable 1 }

		
		HwNbCommonEntry ::=
			SEQUENCE { 
				hwNbIfIndex
					InterfaceIndex,
				hwNbLoopback
					INTEGER,
				hwNbPortType
					INTEGER,
				hwNbAcBlock
					INTEGER,
				hwNbTimeDelayMaster
					Integer32,
				hwNbTimeDelaySlave
					Integer32,
				hwNbRealTimeDelay
					Integer32
			 }

		-- 1.3.6.1.4.1.2011.5.25.157.1.23.5.1.1
		hwNbIfIndex OBJECT-TYPE
			SYNTAX InterfaceIndex
			MAX-ACCESS not-accessible
			STATUS current
			DESCRIPTION
				"The value of this object identifies the index of an narrowband interface."
			::= { hwNbCommonEntry 1 }

		
		-- 1.3.6.1.4.1.2011.5.25.157.1.23.5.1.2
		hwNbLoopback OBJECT-TYPE
			SYNTAX INTEGER
				{
				stopLoopback(1),
				local(2),
				remote(3),
				otherLoop(4)
				}
			MAX-ACCESS read-write
			STATUS current
			DESCRIPTION
				"The local loopback of an narrowband interface is used to test the interface itself.
				By default, stopLoopback is used."
			::= { hwNbCommonEntry 2 }

		-- 1.3.6.1.4.1.2011.5.25.157.1.23.5.1.3
		hwNbPortType OBJECT-TYPE
			SYNTAX INTEGER
				{
				rs232(1),
				rs485(2),
				rs422(3),
				v24(4),
				x21(5),
				v35(6),
				fxs(7),
				fxo(8),
				em(9),
				c3794(10),
				c64k(11)
				}
			MAX-ACCESS read-only
			STATUS current
			DESCRIPTION
				"This object indicates the type of a serial interface."
			::= { hwNbCommonEntry 3 }

		
		-- 1.3.6.1.4.1.2011.5.25.157.1.23.5.1.4
		hwNbAcBlock OBJECT-TYPE
			SYNTAX INTEGER
				{
				block(1),
				active(2),
				unsupport(255)
				}
			MAX-ACCESS read-only
			STATUS current
			DESCRIPTION
				"This object indicates the AC state of a serial interface."
			::= { hwNbCommonEntry 4 }

		
		-- 1.3.6.1.4.1.2011.5.25.157.1.23.5.1.5
		hwNbTimeDelayMaster OBJECT-TYPE
			SYNTAX Integer32
			MAX-ACCESS read-only
			STATUS current
			DESCRIPTION
				"This object indicates the delay configured for the primary link of a serial interface."
			::= { hwNbCommonEntry 5 }

		
		-- 1.3.6.1.4.1.2011.5.25.157.1.23.5.1.6
		hwNbTimeDelaySlave OBJECT-TYPE
			SYNTAX Integer32
			MAX-ACCESS read-only
			STATUS current
			DESCRIPTION
				"This object indicates the delay configured for the secondary link of a serial interface."
			::= { hwNbCommonEntry 6 }

		
		-- 1.3.6.1.4.1.2011.5.25.157.1.23.5.1.7
		hwNbRealTimeDelay OBJECT-TYPE
			SYNTAX Integer32
			MAX-ACCESS read-only
			STATUS current
			DESCRIPTION
				"This object indicates the real-time delay of a serial interface."
			::= { hwNbCommonEntry 7 }

		
		-- 1.3.6.1.4.1.2011.5.25.157.1.24
		hwLinkHeartbeat OBJECT IDENTIFIER ::= { hwPortMIBObjects 24 }
		
		-- 1.3.6.1.4.1.2011.5.25.157.1.24.1
		hwLinkHeartbeatFaultTable OBJECT-TYPE
			SYNTAX SEQUENCE OF HwLinkHeartbeatFaultEntry
			MAX-ACCESS not-accessible
			STATUS current
			DESCRIPTION
				"Link-heartbeat alarm fault info table.The table that contains send
				packets interface and receive packets interface information currently
				operating on this device."
			::= { hwLinkHeartbeat 1 }
		
		-- 1.3.6.1.4.1.2011.5.25.157.1.24.1.1
		hwLinkHeartbeatFaultEntry OBJECT-TYPE
			SYNTAX HwLinkHeartbeatFaultEntry
			MAX-ACCESS not-accessible
			STATUS current
			DESCRIPTION
				"Link-heartbeat alarm fault info entry."
			INDEX { hwLinkHeartbeatIfindex }
			::= { hwLinkHeartbeatFaultTable 1 }
		
		HwLinkHeartbeatFaultEntry ::=
			SEQUENCE { 
				hwLinkHeartbeatIfindex
					InterfaceIndex,
				hwLinkHeartbeatIfName
					OCTET STRING,
				hwLinkHeartbeatTxInterface
					OCTET STRING,
				hwLinkHeartbeatRxInterface
					OCTET STRING
			 }

		-- 1.3.6.1.4.1.2011.5.25.157.1.24.1.1.1
		hwLinkHeartbeatIfindex OBJECT-TYPE
			SYNTAX InterfaceIndex
			MAX-ACCESS read-only
			STATUS current
			DESCRIPTION
				"The interface index."
			::= { hwLinkHeartbeatFaultEntry 1 }
		
		-- 1.3.6.1.4.1.2011.5.25.157.1.24.1.1.2
		hwLinkHeartbeatIfName OBJECT-TYPE
			SYNTAX OCTET STRING (SIZE (0..64))
			MAX-ACCESS read-only
			STATUS current
			DESCRIPTION
				"The interface name."
			::= { hwLinkHeartbeatFaultEntry 2 }
		
		-- 1.3.6.1.4.1.2011.5.25.157.1.24.1.1.3
		hwLinkHeartbeatTxInterface OBJECT-TYPE
			SYNTAX OCTET STRING (SIZE (0..64))
			MAX-ACCESS read-only
			STATUS current
			DESCRIPTION
				"The send physical interface name."
			::= { hwLinkHeartbeatFaultEntry 3 }
		
		-- 1.3.6.1.4.1.2011.5.25.157.1.24.1.1.4
		hwLinkHeartbeatRxInterface OBJECT-TYPE
			SYNTAX OCTET STRING (SIZE (0..64))
			MAX-ACCESS read-only
			STATUS current
			DESCRIPTION
				"The receive physical interface name."
			::= { hwLinkHeartbeatFaultEntry 4 }
		

    hwPortNotifications OBJECT IDENTIFIER ::= { hwPortMIB 2 }

    hwPortACRMasterPWChange NOTIFICATION-TYPE
        OBJECTS {
            hwDs0ChannelBundleParentIfIndex,
            hwDs0ChannelBundleDs1ChannelId,
            hwDs0ChannelBundleId,
            hwDs0ChannelBundlePortName,
            hwDs0ChannelBundleIsMasterPW,
            hwDs0ChannelBundleMasterPWStatus}
        STATUS current
        DESCRIPTION
            "CES-ACR master PW change notification,indicates master pw change or master pw status change,this may happen when a
                pw is deleted or the pw status change."
        ::= { hwPortNotifications 1 }

    hwDslImaGroupTraps OBJECT IDENTIFIER ::= { hwPortNotifications 2 }

    hwDslImaGroupLEDown NOTIFICATION-TYPE
        OBJECTS {
            hwDslGroupImaIfIndex,
            hwDslGroupImaIfName}
        STATUS current
        DESCRIPTION
            "The ima group local edge down notification."
        ::= { hwDslImaGroupTraps 1 }

    hwDslImaGroupLEUp NOTIFICATION-TYPE
        OBJECTS {
            hwDslGroupImaIfIndex,
            hwDslGroupImaIfName}
        STATUS current
        DESCRIPTION
            "The ima group local edge up notification."
        ::= { hwDslImaGroupTraps 2 }

    hwDslImaGroupREDown NOTIFICATION-TYPE
        OBJECTS {
            hwDslGroupImaIfIndex,
            hwDslGroupImaIfName}
        STATUS current
        DESCRIPTION
            "The ima group remote edge down notification."
        ::= { hwDslImaGroupTraps 3 }

    hwDslImaGroupREUp NOTIFICATION-TYPE
        OBJECTS {
            hwDslGroupImaIfIndex,
            hwDslGroupImaIfName}
        STATUS current
        DESCRIPTION
            "The ima group remote edge up notification."
        ::= { hwDslImaGroupTraps 4 }

    hwDslImaLinkTraps OBJECT IDENTIFIER ::= { hwPortNotifications 3 }

    hwDslImaLinkLif NOTIFICATION-TYPE
        OBJECTS {
            hwDslGroupImaIfIndex,
            hwDslLinkIfIndex,
            hwDslGroupImaIfName,
            hwDslLinkIfName}
        STATUS current
        DESCRIPTION
            "The ima link lif notification."
        ::= { hwDslImaLinkTraps 1 }

    hwDslImaLinkLifResume NOTIFICATION-TYPE
        OBJECTS {
            hwDslGroupImaIfIndex,
            hwDslLinkIfIndex,
            hwDslGroupImaIfName,
            hwDslLinkIfName}
        STATUS current
        DESCRIPTION
            "The ima link lif resume notification."
        ::= { hwDslImaLinkTraps 2 }

    hwDslImaLinkLods NOTIFICATION-TYPE
        OBJECTS {
            hwDslGroupImaIfIndex,
            hwDslLinkIfIndex,
            hwDslGroupImaIfName,
            hwDslLinkIfName}
        STATUS current
        DESCRIPTION
            "The ima link lods notification."
        ::= { hwDslImaLinkTraps 3 }

    hwDslImaLinkLodsResume NOTIFICATION-TYPE
        OBJECTS {
            hwDslGroupImaIfIndex,
            hwDslLinkIfIndex,
            hwDslGroupImaIfName,
            hwDslLinkIfName}
        STATUS current
        DESCRIPTION
            "The ima link lods resume notification."
        ::= { hwDslImaLinkTraps 4 }

    hwDslImaLinkRfi NOTIFICATION-TYPE
        OBJECTS {
            hwDslGroupImaIfIndex,
            hwDslLinkIfIndex,
            hwDslGroupImaIfName,
            hwDslLinkIfName}
        STATUS current
        DESCRIPTION
            "The ima link rfi notification."
        ::= { hwDslImaLinkTraps 5 }

    hwDslImaLinkRfiResume NOTIFICATION-TYPE
        OBJECTS {
            hwDslGroupImaIfIndex,
            hwDslLinkIfIndex,
            hwDslGroupImaIfName,
            hwDslLinkIfName}
        STATUS current
        DESCRIPTION
            "The ima link rfi resume notification."
        ::= { hwDslImaLinkTraps 6 }

    hwDslImaLinkReTxUnusable NOTIFICATION-TYPE
        OBJECTS {
            hwDslGroupImaIfIndex,
            hwDslLinkIfIndex,
            hwDslGroupImaIfName,
            hwDslLinkIfName}
        STATUS current
        DESCRIPTION
            "The ima link remote tx unusable notification."
        ::= { hwDslImaLinkTraps 7 }

    hwDslImaLinkReTxUsable NOTIFICATION-TYPE
        OBJECTS {
            hwDslGroupImaIfIndex,
            hwDslLinkIfIndex,
            hwDslGroupImaIfName,
            hwDslLinkIfName}
        STATUS current
        DESCRIPTION
            "The ima link remote tx usable notification."
        ::= { hwDslImaLinkTraps 8 }

    hwDslImaLinkReRxUnusable NOTIFICATION-TYPE
        OBJECTS {
            hwDslGroupImaIfIndex,
            hwDslLinkIfIndex,
            hwDslGroupImaIfName,
            hwDslLinkIfName}
        STATUS current
        DESCRIPTION
            "The ima link remote rx unusable notification."
        ::= { hwDslImaLinkTraps 9 }

    hwDslImaLinkReRxUsable NOTIFICATION-TYPE
        OBJECTS {
            hwDslGroupImaIfIndex,
            hwDslLinkIfIndex,
            hwDslGroupImaIfName,
            hwDslLinkIfName}
        STATUS current
        DESCRIPTION
            "The ima link remote tx usable notification."
        ::= { hwDslImaLinkTraps 10 }

    hwDslLinkTraps OBJECT IDENTIFIER ::= { hwPortNotifications 4 }

    hwDslLinkFrameLost NOTIFICATION-TYPE
        OBJECTS {
            hwBoundDslGroupIfIndex,
            hwDslLinkIfIndex,
            hwBoundDslGroupIfName,
            hwDslLinkIfName}
        STATUS current
        DESCRIPTION
            "The dsl link frame lost notification."
        ::= { hwDslLinkTraps 1 }

    hwDslLinkFrameResume NOTIFICATION-TYPE
        OBJECTS {
            hwBoundDslGroupIfIndex,
            hwDslLinkIfIndex,
            hwBoundDslGroupIfName,
            hwDslLinkIfName}
        STATUS current
        DESCRIPTION
            "The dsl link frame resume notification."
        ::= { hwDslLinkTraps 2 }

    hwDslLinkSignalLost NOTIFICATION-TYPE
        OBJECTS {
            hwBoundDslGroupIfIndex,
            hwDslLinkIfIndex,
            hwBoundDslGroupIfName,
            hwDslLinkIfName,
            hwPhysicalPortAlarmName}
        STATUS current
        DESCRIPTION
            "The dsl link signal lost notification."
        ::= { hwDslLinkTraps 3 }

    hwDslLinkSignalResume NOTIFICATION-TYPE
        OBJECTS {
            hwBoundDslGroupIfIndex,
            hwDslLinkIfIndex,
            hwBoundDslGroupIfName,
            hwDslLinkIfName,
            hwPhysicalPortAlarmName}
        STATUS current
        DESCRIPTION
            "The dsl link signal resume notification."
        ::= { hwDslLinkTraps 4 }

    hwCesPwRemoteLosPktAlarm NOTIFICATION-TYPE
        OBJECTS {
            hwPWCesVcID,
            hwPWCesVcType,
            hwPeerIpAddr,
            hwPWPortName}
        STATUS current
        DESCRIPTION
            "Indicates the alarm is detected."
        ::= { hwPortNotifications 5 }

    hwCesPwRemoteLosPktAlarmResume NOTIFICATION-TYPE
        OBJECTS {
            hwPWCesVcID,
            hwPWCesVcType,
            hwPeerIpAddr,
            hwPWPortName}
        STATUS current
        DESCRIPTION
            "Indicates the alarm is cleared."
        ::= { hwPortNotifications 6 }

    hwCesPwOppositeRai NOTIFICATION-TYPE
        OBJECTS {
            hwPWCesVcID,
            hwPWCesVcType,
            hwPeerIpAddr,
            hwPWPortName}
        STATUS current
        DESCRIPTION
            "Indicates the alarm is detected."
        ::= { hwPortNotifications 7 }

    hwCesPwOppositeRaiResume NOTIFICATION-TYPE
        OBJECTS {
            hwPWCesVcID,
            hwPWCesVcType,
            hwPeerIpAddr,
            hwPWPortName}
        STATUS current
        DESCRIPTION
            "Indicates the alarm is cleared."
        ::= { hwPortNotifications 8 }

    hwLosAlarm NOTIFICATION-TYPE
        OBJECTS {
            hwPhysicalPortInSlot,
            hwPhysicalPortInCard,
            hwPhysicalPortInPort,
            hwPhysicalPortName,
            hwPhysicalPortAlarmName}
        STATUS current
        DESCRIPTION
            "This object indicates that an alarm is generated due to signal loss at the receive end."
        ::= { hwPortNotifications 9 }

    hwLosAlarmResume NOTIFICATION-TYPE
        OBJECTS {
            hwPhysicalPortInSlot,
            hwPhysicalPortInCard,
            hwPhysicalPortInPort,
            hwPhysicalPortName,
            hwPhysicalPortAlarmName}
        STATUS current
        DESCRIPTION
            "This object indicates that a clear alarm is generated when signal loss at the receive end stops."
        ::= { hwPortNotifications 10 }

    hwLofAlarm NOTIFICATION-TYPE
        OBJECTS {
            hwPhysicalPortInSlot,
            hwPhysicalPortInCard,
            hwPhysicalPortInPort,
            hwPhysicalPortName}
        STATUS current
        DESCRIPTION
            "This object indicates that an out of frame (OOF) alarm is generated at the receive end."
        ::= { hwPortNotifications 11 }

    hwLofAlarmResume NOTIFICATION-TYPE
        OBJECTS {
            hwPhysicalPortInSlot,
            hwPhysicalPortInCard,
            hwPhysicalPortInPort,
            hwPhysicalPortName}
        STATUS current
        DESCRIPTION
            "This object indicates that a clear alarm is generated when frame loss at the receive end stops."
        ::= { hwPortNotifications 12 }

    hwOofAlarm NOTIFICATION-TYPE
        OBJECTS {
            hwPhysicalPortInSlot,
            hwPhysicalPortInCard,
            hwPhysicalPortInPort,
            hwPhysicalPortName}
        STATUS current
        DESCRIPTION
            "This object indicates that an out of frame (OOF) alarm is generated at the receive end."
        ::= { hwPortNotifications 13 }

    hwOofAlarmResume NOTIFICATION-TYPE
        OBJECTS {
            hwPhysicalPortInSlot,
            hwPhysicalPortInCard,
            hwPhysicalPortInPort,
            hwPhysicalPortName}
        STATUS current
        DESCRIPTION
            "This object indicates that the OOF alarm generated at the receive end is cleared."
        ::= { hwPortNotifications 14 }

    hwB1TcaAlarm NOTIFICATION-TYPE
        OBJECTS {
            hwPhysicalPortInSlot,
            hwPhysicalPortInCard,
            hwPhysicalPortInPort,
            hwPhysicalPortName}
        STATUS current
        DESCRIPTION
            "This object indicates that the number of error bits for the B1 RS exceeds a specified threshold."
        ::= { hwPortNotifications 15 }

    hwB1TcaAlarmResume NOTIFICATION-TYPE
        OBJECTS {
            hwPhysicalPortInSlot,
            hwPhysicalPortInCard,
            hwPhysicalPortInPort,
            hwPhysicalPortName}
        STATUS current
        DESCRIPTION
            "This object indicates that the number of error bits for the B1 RS falls below the specified threshold."
        ::= { hwPortNotifications 16 }

    hwB2TcaAlarm NOTIFICATION-TYPE
        OBJECTS {
            hwPhysicalPortInSlot,
            hwPhysicalPortInCard,
            hwPhysicalPortInPort,
            hwPhysicalPortName}
        STATUS current
        DESCRIPTION
            "This object indicates that the number of error bits for the B2 RS exceeds a specified threshold."
        ::= { hwPortNotifications 17 }

    hwB2TcaAlarmResume NOTIFICATION-TYPE
        OBJECTS {
            hwPhysicalPortInSlot,
            hwPhysicalPortInCard,
            hwPhysicalPortInPort,
            hwPhysicalPortName}
        STATUS current
        DESCRIPTION
            "This object indicates that the number of error bits for the B2 RS falls below the specified threshold."
        ::= { hwPortNotifications 18 }

    hwJ0TimAlarm NOTIFICATION-TYPE
        OBJECTS {
            hwPhysicalPortInSlot,
            hwPhysicalPortInCard,
            hwPhysicalPortInPort,
            hwPhysicalPortName}
        STATUS current
        DESCRIPTION
            "This object indicates that an alarm for trace identifier mismatch is generated."
        ::= { hwPortNotifications 19 }

    hwJ0TimAlarmResume NOTIFICATION-TYPE
        OBJECTS {
            hwPhysicalPortInSlot,
            hwPhysicalPortInCard,
            hwPhysicalPortInPort,
            hwPhysicalPortName}
        STATUS current
        DESCRIPTION
            "This object indicates that the alarm for trace identifier mismatch is cleared."
        ::= { hwPortNotifications 20 }

    hwLrdiAlarm NOTIFICATION-TYPE
        OBJECTS {
            hwPhysicalPortInSlot,
            hwPhysicalPortInCard,
            hwPhysicalPortInPort,
            hwPhysicalPortName}
        STATUS current
        DESCRIPTION
            "This object indicates that a line remote defect indicator (LRDI) alarm is generated in the multiplex section (MS) at the remote end."
        ::= { hwPortNotifications 21 }

    hwLrdiAlarmResume NOTIFICATION-TYPE
        OBJECTS {
            hwPhysicalPortInSlot,
            hwPhysicalPortInCard,
            hwPhysicalPortInPort,
            hwPhysicalPortName}
        STATUS current
        DESCRIPTION
            "This object indicates that the LRDI alarm generated in the MS at the remote end is cleared."
        ::= { hwPortNotifications 22 }

    hwSfbereAlarm NOTIFICATION-TYPE
        OBJECTS {
            hwPhysicalPortInSlot,
            hwPhysicalPortInCard,
            hwPhysicalPortInPort,
            hwPhysicalPortName}
        STATUS current
        DESCRIPTION
            "This object indicates that the number of error bits for the B2 RS exceeds a specified threshold."
        ::= { hwPortNotifications 23 }

    hwSfbereAlarmResume NOTIFICATION-TYPE
        OBJECTS {
            hwPhysicalPortInSlot,
            hwPhysicalPortInCard,
            hwPhysicalPortInPort,
            hwPhysicalPortName}
        STATUS current
        DESCRIPTION
            "This object indicates that the number of error bits for the B2 RS falls below the specified threshold."
        ::= { hwPortNotifications 24 }

    hwAuLopAlarm NOTIFICATION-TYPE
        OBJECTS {
            hwPhysicalPortInSlot,
            hwPhysicalPortInCard,
            hwPhysicalPortInPort,
            hwPhysicalPortName}
        STATUS current
        DESCRIPTION
            "This object indicates the loss of the AU pointer."
        ::= { hwPortNotifications 25 }

    hwAuLopAlarmResume NOTIFICATION-TYPE
        OBJECTS {
            hwPhysicalPortInSlot,
            hwPhysicalPortInCard,
            hwPhysicalPortInPort,
            hwPhysicalPortName}
        STATUS current
        DESCRIPTION
            "This object indicates that the alarm for the loss of the AU pointer is cleared."
        ::= { hwPortNotifications 26 }

    hwLaisAlarm NOTIFICATION-TYPE
        OBJECTS {
            hwPhysicalPortInSlot,
            hwPhysicalPortInCard,
            hwPhysicalPortInPort,
            hwPhysicalPortName}
        STATUS current
        DESCRIPTION
            "This object indicates the indication signal alarm in the MS."
        ::= { hwPortNotifications 27 }

    hwLaisAlarmResume NOTIFICATION-TYPE
        OBJECTS {
            hwPhysicalPortInSlot,
            hwPhysicalPortInCard,
            hwPhysicalPortInPort,
            hwPhysicalPortName}
        STATUS current
        DESCRIPTION
            "This object indicates that the indication signal alarm in the MS is cleared."
        ::= { hwPortNotifications 28 }

    hwSdbereAlarm NOTIFICATION-TYPE
        OBJECTS {
            hwPhysicalPortInSlot,
            hwPhysicalPortInCard,
            hwPhysicalPortInPort,
            hwPhysicalPortName}
        STATUS current
        DESCRIPTION
            "This object indicates the signal degrade in the B2 MS."
        ::= { hwPortNotifications 29 }

    hwSdbereAlarmResume NOTIFICATION-TYPE
        OBJECTS {
            hwPhysicalPortInSlot,
            hwPhysicalPortInCard,
            hwPhysicalPortInPort,
            hwPhysicalPortName}
        STATUS current
        DESCRIPTION
            "This object indicates that the alarm for the signal degrade in the B2 MS is cleared."
        ::= { hwPortNotifications 30 }

    hwPtimAlarm NOTIFICATION-TYPE
        OBJECTS {
            hwPhysicalPortInSlot,
            hwPhysicalPortInCard,
            hwPhysicalPortInPort,
            hwPortPhysicalHpIndex,
			hwPhysicalPortName}
        STATUS current
        DESCRIPTION
            "This object indicates that an alarm is generated when the higher order path (HP) trace identifier is unstable."
        ::= { hwPortNotifications 31 }

    hwPtimAlarmResume NOTIFICATION-TYPE
        OBJECTS {
            hwPhysicalPortInSlot,
            hwPhysicalPortInCard,
            hwPhysicalPortInPort,
            hwPortPhysicalHpIndex,
			hwPhysicalPortName}
        STATUS current
        DESCRIPTION
            "This object indicates that a clear alarm is generated when the higher order path (HP) trace identifier becomes stable."
        ::= { hwPortNotifications 32 }

    hwPuneqAlarm NOTIFICATION-TYPE
        OBJECTS {
            hwPhysicalPortInSlot,
            hwPhysicalPortInCard,
            hwPhysicalPortInPort,
            hwPortPhysicalHpIndex,
			hwPhysicalPortName}
        STATUS current
        DESCRIPTION
            "This object indicates that an alarm is generated when the higher order path (HP) is unequipped."
        ::= { hwPortNotifications 33 }

    hwPuneqAlarmResume NOTIFICATION-TYPE
        OBJECTS {
            hwPhysicalPortInSlot,
            hwPhysicalPortInCard,
            hwPhysicalPortInPort,
            hwPortPhysicalHpIndex,
			hwPhysicalPortName}
        STATUS current
        DESCRIPTION
            "This object indicates that a clear alarm is generated when the higher order path (HP) is equipped."
        ::= { hwPortNotifications 34 }

    hwPrdiAlarm NOTIFICATION-TYPE
        OBJECTS {
            hwPhysicalPortInSlot,
            hwPhysicalPortInCard,
            hwPhysicalPortInPort,
            hwPortPhysicalHpIndex,
			hwPhysicalPortName}
        STATUS current
        DESCRIPTION
            "This object indicates the higher order path (HP) Remote Default Indication (HPRDI) alarm."
        ::= { hwPortNotifications 35 }

    hwPrdiAlarmResume NOTIFICATION-TYPE
        OBJECTS {
            hwPhysicalPortInSlot,
            hwPhysicalPortInCard,
            hwPhysicalPortInPort,
            hwPortPhysicalHpIndex,
			hwPhysicalPortName}
        STATUS current
        DESCRIPTION
            "This object indicates that the HPRDI alarm is cleared."
        ::= { hwPortNotifications 36 }

    hwB3TcaAlarm NOTIFICATION-TYPE
        OBJECTS {
            hwPhysicalPortInSlot,
            hwPhysicalPortInCard,
            hwPhysicalPortInPort,
            hwPortPhysicalHpIndex,
			hwPhysicalPortName}
        STATUS current
        DESCRIPTION
            "This object indicates that the number of bit errors on the B3 higher order path (HP) exceeds the upper threshold."
        ::= { hwPortNotifications 37 }

    hwB3TcaAlarmResume NOTIFICATION-TYPE
        OBJECTS {
            hwPhysicalPortInSlot,
            hwPhysicalPortInCard,
            hwPhysicalPortInPort,
            hwPortPhysicalHpIndex,
			hwPhysicalPortName}
        STATUS current
        DESCRIPTION
            "This object indicates that the number of bit errors on the B3 higher order path (HP) falls below the upper threshold."
        ::= { hwPortNotifications 38 }

    hwPplmAlarm NOTIFICATION-TYPE
        OBJECTS {
            hwPhysicalPortInSlot,
            hwPhysicalPortInCard,
            hwPhysicalPortInPort,
            hwPortPhysicalHpIndex,
			hwPhysicalPortName}
        STATUS current
        DESCRIPTION
            "This object indicates the higher order path (HP) signal identifier mismatch."
        ::= { hwPortNotifications 39 }

    hwPplmAlarmResume NOTIFICATION-TYPE
        OBJECTS {
            hwPhysicalPortInSlot,
            hwPhysicalPortInCard,
            hwPhysicalPortInPort,
            hwPortPhysicalHpIndex,
			hwPhysicalPortName}
        STATUS current
        DESCRIPTION
            "This object indicates that the higher order path (HP) signal identifier mismatch is rectified."
        ::= { hwPortNotifications 40 }

    hwPaisAlarm NOTIFICATION-TYPE
        OBJECTS {
            hwPhysicalPortInSlot,
            hwPhysicalPortInCard,
            hwPhysicalPortInPort,
            hwPortPhysicalHpIndex,
			hwPhysicalPortName}
        STATUS current
        DESCRIPTION
            "This object indicates that a path alarm indication signal is detected."
        ::= { hwPortNotifications 41 }

    hwPaisAlarmResume NOTIFICATION-TYPE
        OBJECTS {
            hwPhysicalPortInSlot,
            hwPhysicalPortInCard,
            hwPhysicalPortInPort,
            hwPortPhysicalHpIndex,
			hwPhysicalPortName}
        STATUS current
        DESCRIPTION
            "This object indicates that the path alarm indication signal is removed."
        ::= { hwPortNotifications 42 }

    hwAuAisAlarm NOTIFICATION-TYPE
        OBJECTS {
            hwPhysicalPortInSlot,
            hwPhysicalPortInCard,
            hwPhysicalPortInPort,
            hwPortPhysicalHpIndex,
            hwPhysicalPortName}
        STATUS current
        DESCRIPTION
            "This object indicates that a higher order path (HP) indication signal alarm is generated."
        ::= { hwPortNotifications 43 }

    hwAuAisAlarmResume NOTIFICATION-TYPE
        OBJECTS {
            hwPhysicalPortInSlot,
            hwPhysicalPortInCard,
            hwPhysicalPortInPort,
            hwPortPhysicalHpIndex,
            hwPhysicalPortName}
        STATUS current
        DESCRIPTION
            "This object indicates that the higher order path (HP) indication signal alarm is cleared."
        ::= { hwPortNotifications 44 }

    hwVlopAlarm NOTIFICATION-TYPE
        OBJECTS {
            hwPhysicalPortInSlot,
            hwPhysicalPortInCard,
            hwPhysicalPortInPort,
            hwPortPhysicalHpIndex,
            hwPortPhysicalLpIndex,
            hwPhysicalPortName}
        STATUS current
        DESCRIPTION
            "This object indicates that an alarm is generated when the administrative unit (AU) pointer is lost."
        ::= { hwPortNotifications 45 }

    hwVlopAlarmResume NOTIFICATION-TYPE
        OBJECTS {
            hwPhysicalPortInSlot,
            hwPhysicalPortInCard,
            hwPhysicalPortInPort,
            hwPortPhysicalHpIndex,
            hwPortPhysicalLpIndex,
            hwPhysicalPortName}
        STATUS current
        DESCRIPTION
            "This object indicates that the alarm generated due to the loss of the AU pointer is cleared."
        ::= { hwPortNotifications 46 }

    hwLomAlarm NOTIFICATION-TYPE
        OBJECTS {
            hwPhysicalPortInSlot,
            hwPhysicalPortInCard,
            hwPhysicalPortInPort,
            hwPortPhysicalHpIndex,
			hwPhysicalPortName}
        STATUS current
        DESCRIPTION
            "This object indicates the loss of multiframe (LOM) on the higher order path (HP)."
        ::= { hwPortNotifications 47 }

    hwLomAlarmResume NOTIFICATION-TYPE
        OBJECTS {
            hwPhysicalPortInSlot,
            hwPhysicalPortInCard,
            hwPhysicalPortInPort,
            hwPortPhysicalHpIndex,
			hwPhysicalPortName}
        STATUS current
        DESCRIPTION
            "This object indicates that the LOM on the higher order path (HP) is resolved."
        ::= { hwPortNotifications 48 }

    hwLpTimVc12Alarm NOTIFICATION-TYPE
        OBJECTS {
            hwPhysicalPortInSlot,
            hwPhysicalPortInCard,
            hwPhysicalPortInPort,
            hwPortPhysicalHpIndex,
            hwPortPhysicalLpIndex,
            hwPhysicalPortName}
        STATUS current
        DESCRIPTION
            "Indicates the alarm is detected."
        ::= { hwPortNotifications 49 }

    hwLpTimVc12AlarmResume NOTIFICATION-TYPE
        OBJECTS {
            hwPhysicalPortInSlot,
            hwPhysicalPortInCard,
            hwPhysicalPortInPort,
            hwPortPhysicalHpIndex,
            hwPortPhysicalLpIndex,
            hwPhysicalPortName}
        STATUS current
        DESCRIPTION
            "Indicates the alarm is cleared."
        ::= { hwPortNotifications 50 }

    hwLpUneqVc12Alarm NOTIFICATION-TYPE
        OBJECTS {
            hwPhysicalPortInSlot,
            hwPhysicalPortInCard,
            hwPhysicalPortInPort,
            hwPortPhysicalHpIndex,
            hwPortPhysicalLpIndex,
            hwPhysicalPortName}
        STATUS current
        DESCRIPTION
            "This object indicates that a lower order path (LP) unequipped indication signal (PUNEQ) alarm is generated."
        ::= { hwPortNotifications 51 }

    hwLpUneqVc12AlarmResume NOTIFICATION-TYPE
        OBJECTS {
            hwPhysicalPortInSlot,
            hwPhysicalPortInCard,
            hwPhysicalPortInPort,
            hwPortPhysicalHpIndex,
            hwPortPhysicalLpIndex,
            hwPhysicalPortName}
        STATUS current
        DESCRIPTION
            "This object indicates that the PUNEQ alarm is cleared."
        ::= { hwPortNotifications 52 }

    hwVrdiAlarm NOTIFICATION-TYPE
        OBJECTS {
            hwPhysicalPortInSlot,
            hwPhysicalPortInCard,
            hwPhysicalPortInPort,
            hwPortPhysicalHpIndex,
            hwPortPhysicalLpIndex,
            hwPhysicalPortName}
        STATUS current
        DESCRIPTION
            "This object indicates that a lower order path (LP) remote defect indication (PRDI) alarm is generated."
        ::= { hwPortNotifications 53 }

    hwVrdiAlarmResume NOTIFICATION-TYPE
        OBJECTS {
            hwPhysicalPortInSlot,
            hwPhysicalPortInCard,
            hwPhysicalPortInPort,
            hwPortPhysicalHpIndex,
            hwPortPhysicalLpIndex,
            hwPhysicalPortName}
        STATUS current
        DESCRIPTION
            "This object indicates that the PRDI alarm is cleared."
        ::= { hwPortNotifications 54 }

    hwBip2TcaAlarm NOTIFICATION-TYPE
        OBJECTS {
            hwPhysicalPortInSlot,
            hwPhysicalPortInCard,
            hwPhysicalPortInPort,
            hwPortPhysicalHpIndex,
            hwPortPhysicalLpIndex,
            hwPhysicalPortName}
        STATUS current
        DESCRIPTION
            "This object indicates that an alarm is generated for the BIP signal degrade."
        ::= { hwPortNotifications 57 }

    hwBip2TcaAlarmResume NOTIFICATION-TYPE
        OBJECTS {
            hwPhysicalPortInSlot,
            hwPhysicalPortInCard,
            hwPhysicalPortInPort,
            hwPortPhysicalHpIndex,
            hwPortPhysicalLpIndex,
            hwPhysicalPortName}
        STATUS current
        DESCRIPTION
            "This object indicates that the alarm for the BIP signal degrade is cleared."
        ::= { hwPortNotifications 58 }

    hwLpSlmVc12Alarm NOTIFICATION-TYPE
        OBJECTS {
            hwPhysicalPortInSlot,
            hwPhysicalPortInCard,
            hwPhysicalPortInPort,
            hwPortPhysicalHpIndex,
            hwPortPhysicalLpIndex,
            hwPhysicalPortName}
        STATUS current
        DESCRIPTION
            "This object indicates a lower order path (LP) signal label mismatch alarm."
        ::= { hwPortNotifications 59 }

    hwLpSlmVc12AlarmResume NOTIFICATION-TYPE
        OBJECTS {
            hwPhysicalPortInSlot,
            hwPhysicalPortInCard,
            hwPhysicalPortInPort,
            hwPortPhysicalHpIndex,
            hwPortPhysicalLpIndex,
            hwPhysicalPortName}
        STATUS current
        DESCRIPTION
            "This object indicates that the lower order path (LP) signal label mismatch alarm is cleared."
        ::= { hwPortNotifications 60 }

    hwTuAisVc12Alarm NOTIFICATION-TYPE
        OBJECTS {
            hwPhysicalPortInSlot,
            hwPhysicalPortInCard,
            hwPhysicalPortInPort,
            hwPortPhysicalHpIndex,
            hwPortPhysicalLpIndex,
            hwPhysicalPortName}
        STATUS current
        DESCRIPTION
            "This object indicates TU alarm indication."
        ::= { hwPortNotifications 61 }

    hwTuAisVc12AlarmResume NOTIFICATION-TYPE
        OBJECTS {
            hwPhysicalPortInSlot,
            hwPhysicalPortInCard,
            hwPhysicalPortInPort,
            hwPortPhysicalHpIndex,
            hwPortPhysicalLpIndex,
            hwPhysicalPortName}
        STATUS current
        DESCRIPTION
            "This object indicates that the TU alarm is cleared."
        ::= { hwPortNotifications 62 }

    hwE1EsTcaAlarm NOTIFICATION-TYPE
        OBJECTS {
            hwPhysicalPortInSlot,
            hwPhysicalPortInCard,
            hwPhysicalPortInPort,
            hwPhysicalPortName}
        STATUS current
        DESCRIPTION
            "This object indicates that the number of errored seconds exceeds a specified threshold."
        ::= { hwPortNotifications 63 }

    hwE1EsTcaAlarmResume NOTIFICATION-TYPE
        OBJECTS {
            hwPhysicalPortInSlot,
            hwPhysicalPortInCard,
            hwPhysicalPortInPort,
            hwPhysicalPortName}
        STATUS current
        DESCRIPTION
            "This object indicates that the number of errored seconds falls below a specified threshold."
        ::= { hwPortNotifications 64 }

    hwE1LmfaAlarm NOTIFICATION-TYPE
        OBJECTS {
            hwPhysicalPortInSlot,
            hwPhysicalPortInCard,
            hwPhysicalPortInPort,
            hwPhysicalPortName}
        STATUS current
        DESCRIPTION
            "This object indicates an LOM alarm on the framed E1."
        ::= { hwPortNotifications 67 }

    hwE1LmfaAlarmResume NOTIFICATION-TYPE
        OBJECTS {
            hwPhysicalPortInSlot,
            hwPhysicalPortInCard,
            hwPhysicalPortInPort,
            hwPhysicalPortName}
        STATUS current
        DESCRIPTION
            "This object indicates that the LOM alarm on the framed E1 is cleared."
        ::= { hwPortNotifications 68 }

    hwE1UpE1AisAlarm NOTIFICATION-TYPE
        OBJECTS {
            hwPhysicalPortInSlot,
            hwPhysicalPortInCard,
            hwPhysicalPortInPort,
            hwPhysicalPortName}
        STATUS current
        DESCRIPTION
            "This object indicates that an upstream alarm indication signal is generated on an E1 interface."
        ::= { hwPortNotifications 69 }

    hwE1UpE1AisAlarmResume NOTIFICATION-TYPE
        OBJECTS {
            hwPhysicalPortInSlot,
            hwPhysicalPortInCard,
            hwPhysicalPortInPort,
            hwPhysicalPortName}
        STATUS current
        DESCRIPTION
            "This object indicates that the upstream alarm indication signal generated on an E1 interface is cleared."
        ::= { hwPortNotifications 70 }

    hwE1AlmE1RaiAlarm NOTIFICATION-TYPE
        OBJECTS {
            hwPhysicalPortInSlot,
            hwPhysicalPortInCard,
            hwPhysicalPortInPort,
            hwPhysicalPortName}
        STATUS current
        DESCRIPTION
            "This object indicates that a remote alarm indication (RAI) signal is generated on an E1 link."
        ::= { hwPortNotifications 71 }

    hwE1AlmE1RaiAlarmResume NOTIFICATION-TYPE
        OBJECTS {
            hwPhysicalPortInSlot,
            hwPhysicalPortInCard,
            hwPhysicalPortInPort,
            hwPhysicalPortName}
        STATUS current
        DESCRIPTION
            "This object indicates that the RAI signal generated on an E1 link is cleared."
        ::= { hwPortNotifications 72 }

    hwCesPwOppositeAcFault NOTIFICATION-TYPE
        OBJECTS {
            hwPWCesVcID,
            hwPWCesVcType,
            hwPeerIpAddr,
            hwPWPortName}
        STATUS current
        DESCRIPTION
            "This object indicates that an alarm is generated when the attachment circuit on the peer device goes faulty."
        ::= { hwPortNotifications 73 }

    hwCesPwOppositeAcFaultResume NOTIFICATION-TYPE
        OBJECTS {
            hwPWCesVcID,
            hwPWCesVcType,
            hwPeerIpAddr,
            hwPWPortName}
        STATUS current
        DESCRIPTION
            "This object indicates that a clear alarm is generated when the attachment circuit fault on the peer device is rectified."
        ::= { hwPortNotifications 74 }

    hwCesLosPktExcAlarm NOTIFICATION-TYPE
        OBJECTS {
            hwPWCesVcID,
            hwPWCesVcType,
            hwPeerIpAddr,
            hwPWPortName}
        STATUS current
        DESCRIPTION
            "Indicates the alarm is detected."
        ::= { hwPortNotifications 75 }

    hwCesLosPktExcAlarmResume NOTIFICATION-TYPE
        OBJECTS {
            hwPWCesVcID,
            hwPWCesVcType,
            hwPeerIpAddr,
            hwPWPortName}
        STATUS current
        DESCRIPTION
            "Indicates the alarm is cleared."
        ::= { hwPortNotifications 76 }

    hwCesMisorderPktExcAlarm NOTIFICATION-TYPE
        OBJECTS {
            hwPWCesVcID,
            hwPWCesVcType,
            hwPeerIpAddr,
            hwPWPortName}
        STATUS current
        DESCRIPTION
            "Indicates the alarm is detected."
        ::= { hwPortNotifications 77 }

    hwCesMisorderPktExcAlarmResume NOTIFICATION-TYPE
        OBJECTS {
            hwPWCesVcID,
            hwPWCesVcType,
            hwPeerIpAddr,
            hwPWPortName}
        STATUS current
        DESCRIPTION
            "Indicates the alarm is cleared."
        ::= { hwPortNotifications 78 }

    hwCesStrayPktExcAlarm NOTIFICATION-TYPE
        OBJECTS {
            hwPWCesVcID,
            hwPWCesVcType,
            hwPeerIpAddr,
            hwPWPortName}
        STATUS current
        DESCRIPTION
            "Indicates the alarm is detected."
        ::= { hwPortNotifications 79 }

    hwCesStrayPktExcAlarmResume NOTIFICATION-TYPE
        OBJECTS {
            hwPWCesVcID,
            hwPWCesVcType,
            hwPeerIpAddr,
            hwPWPortName}
        STATUS current
        DESCRIPTION
            "Indicates the alarm is cleared."
        ::= { hwPortNotifications 80 }

    hwCesMalPktExcAlarm NOTIFICATION-TYPE
        OBJECTS {
            hwPWCesVcID,
            hwPWCesVcType,
            hwPeerIpAddr,
            hwPWPortName}
        STATUS current
        DESCRIPTION
            "Indicates the alarm is detected."
        ::= { hwPortNotifications 81 }

    hwCesMalPktExcAlarmResume NOTIFICATION-TYPE
        OBJECTS {
            hwPWCesVcID,
            hwPWCesVcType,
            hwPeerIpAddr,
            hwPWPortName}
        STATUS current
        DESCRIPTION
            "Indicates the alarm is cleared."
        ::= { hwPortNotifications 82 }

    hwCesJtrUdrExcAlarm NOTIFICATION-TYPE
        OBJECTS {
            hwPWCesVcID,
            hwPWCesVcType,
            hwPeerIpAddr,
            hwPWPortName}
        STATUS current
        DESCRIPTION
            "Indicates the alarm is detected."
        ::= { hwPortNotifications 83 }

    hwCesJtrUdrExcAlarmResume NOTIFICATION-TYPE
        OBJECTS {
            hwPWCesVcID,
            hwPWCesVcType,
            hwPeerIpAddr,
            hwPWPortName}
        STATUS current
        DESCRIPTION
            "Indicates the alarm is cleared."
        ::= { hwPortNotifications 84 }

    hwCesJtrOvrExcAlarm NOTIFICATION-TYPE
        OBJECTS {
            hwPWCesVcID,
            hwPWCesVcType,
            hwPeerIpAddr,
            hwPWPortName}
        STATUS current
        DESCRIPTION
            "Indicates the alarm is detected."
        ::= { hwPortNotifications 85 }

    hwCesJtrOvrExcAlarmResume NOTIFICATION-TYPE
        OBJECTS {
            hwPWCesVcID,
            hwPWCesVcType,
            hwPeerIpAddr,
            hwPWPortName}
        STATUS current
        DESCRIPTION
            "Indicates the alarm is cleared."
        ::= { hwPortNotifications 86 }

    hwRroolAlarm NOTIFICATION-TYPE
        OBJECTS {
            hwPhysicalPortInSlot,
            hwPhysicalPortInCard,
            hwPhysicalPortInPort,
            hwPhysicalPortName}
        STATUS current
        DESCRIPTION
            "This object indicates that an alarm is generated when there is no clock on the receive line."
        ::= { hwPortNotifications 87 }

    hwRroolAlarmResume NOTIFICATION-TYPE
        OBJECTS {
            hwPhysicalPortInSlot,
            hwPhysicalPortInCard,
            hwPhysicalPortInPort,
            hwPhysicalPortName}
        STATUS current
        DESCRIPTION
            "This object indicates that a clear alarm is generated when there is a clock on the receive line."
        ::= { hwPortNotifications 88 }

    hwVrfiAlarm NOTIFICATION-TYPE
        OBJECTS {
            hwPhysicalPortInSlot,
            hwPhysicalPortInCard,
            hwPhysicalPortInPort,
            hwPortPhysicalHpIndex,
            hwPortPhysicalLpIndex,
            hwPhysicalPortName}
        STATUS current
        DESCRIPTION
            "This object indicates that an alarm is generated when a lower order path (LP) remote failure indication (RFI) signal is detected."
        ::= { hwPortNotifications 89 }

    hwVrfiAlarmResume NOTIFICATION-TYPE
        OBJECTS {
            hwPhysicalPortInSlot,
            hwPhysicalPortInCard,
            hwPhysicalPortInPort,
            hwPortPhysicalHpIndex,
            hwPortPhysicalLpIndex,
            hwPhysicalPortName}
        STATUS current
        DESCRIPTION
            "This object indicates that a clear alarm is generated when the lower order path (LP) remote failure indication (RFI) signal is cleared."
        ::= { hwPortNotifications 90 }

    hwV5VcaisAlarm NOTIFICATION-TYPE
        OBJECTS {
            hwPhysicalPortInSlot,
            hwPhysicalPortInCard,
            hwPhysicalPortInPort,
            hwPortPhysicalHpIndex,
            hwPortPhysicalLpIndex,
            hwPhysicalPortName}
        STATUS current
        DESCRIPTION
            "This object indicates that an alarm indication signal is generated in the virtual container."
        ::= { hwPortNotifications 91 }

    hwV5VcaisAlarmResume NOTIFICATION-TYPE
        OBJECTS {
            hwPhysicalPortInSlot,
            hwPhysicalPortInCard,
            hwPhysicalPortInPort,
            hwPortPhysicalHpIndex,
            hwPortPhysicalLpIndex,
            hwPhysicalPortName}
        STATUS current
        DESCRIPTION
            "This object indicates that the alarm indication signal generated in the virtual container is cleared."
        ::= { hwPortNotifications 92 }

    hwCposE1AlmE1RaiAlarm NOTIFICATION-TYPE
        OBJECTS {
            hwPhysicalPortInSlot,
            hwPhysicalPortInCard,
            hwPhysicalPortInPort,
            hwPortPhysicalHpIndex,
            hwPortPhysicalLpIndex,
            hwPhysicalPortName}
        STATUS current
        DESCRIPTION
            "This object indicates that an RAI signal is generated on an E1 link channelized from VC12."
        ::= { hwPortNotifications 95 }

    hwCposE1AlmE1RaiAlarmResume NOTIFICATION-TYPE
        OBJECTS {
            hwPhysicalPortInSlot,
            hwPhysicalPortInCard,
            hwPhysicalPortInPort,
            hwPortPhysicalHpIndex,
            hwPortPhysicalLpIndex,
            hwPhysicalPortName}
        STATUS current
        DESCRIPTION
            "This object indicates that the RAI signal generated on an E1 link channelized from VC12 is cleared."
        ::= { hwPortNotifications 96 }

    hwCposE1LfaAlarm NOTIFICATION-TYPE
        OBJECTS {
            hwPhysicalPortInSlot,
            hwPhysicalPortInCard,
            hwPhysicalPortInPort,
            hwPortPhysicalHpIndex,
            hwPortPhysicalLpIndex,
            hwPhysicalPortName}
        STATUS current
        DESCRIPTION
            "This object indicates that an out of frame (OOF) alarm is generated on the framed E1 channelized from VC12."
        ::= { hwPortNotifications 97 }

    hwCposE1LfaAlarmResume NOTIFICATION-TYPE
        OBJECTS {
            hwPhysicalPortInSlot,
            hwPhysicalPortInCard,
            hwPhysicalPortInPort,
            hwPortPhysicalHpIndex,
            hwPortPhysicalLpIndex,
            hwPhysicalPortName}
        STATUS current
        DESCRIPTION
            "This object indicates that the OOF alarm generated on the framed E1 channelized from VC12 is cleared."
        ::= { hwPortNotifications 98 }

    hwCposE1UpE1AisAlarm NOTIFICATION-TYPE
        OBJECTS {
            hwPhysicalPortInSlot,
            hwPhysicalPortInCard,
            hwPhysicalPortInPort,
            hwPortPhysicalHpIndex,
            hwPortPhysicalLpIndex,
            hwPhysicalPortName}
        STATUS current
        DESCRIPTION
            "This object indicates that an upstream alarm indication signal is generated on an E1 link channelized from VC12."
        ::= { hwPortNotifications 99 }

    hwCposE1UpE1AisAlarmResume NOTIFICATION-TYPE
        OBJECTS {
            hwPhysicalPortInSlot,
            hwPhysicalPortInCard,
            hwPhysicalPortInPort,
            hwPortPhysicalHpIndex,
            hwPortPhysicalLpIndex,
            hwPhysicalPortName}
        STATUS current
        DESCRIPTION
            "This object indicates that an upstream alarm indication signal generated on an E1 link channelized from VC12 is cleared."
        ::= { hwPortNotifications 100 }

    hwCposE1DownE1AisAlarm NOTIFICATION-TYPE
        OBJECTS {
            hwPhysicalPortInSlot,
            hwPhysicalPortInCard,
            hwPhysicalPortInPort,
            hwPortPhysicalHpIndex,
            hwPortPhysicalLpIndex,
            hwPhysicalPortName}
        STATUS current
        DESCRIPTION
            "This object indicates that a downstream alarm indication signal is generated on an E1 link channelized from VC12."
        ::= { hwPortNotifications 101 }

    hwCposE1DownE1AisAlarmResume NOTIFICATION-TYPE
        OBJECTS {
            hwPhysicalPortInSlot,
            hwPhysicalPortInCard,
            hwPhysicalPortInPort,
            hwPortPhysicalHpIndex,
            hwPortPhysicalLpIndex,
            hwPhysicalPortName}
        STATUS current
        DESCRIPTION
            "This object indicates that the downstream alarm indication signal generated on an E1 link channelized from VC12 is cleared."
        ::= { hwPortNotifications 102 }

    hwE1DownE1AisAlarm NOTIFICATION-TYPE
        OBJECTS {
            hwPhysicalPortInSlot,
            hwPhysicalPortInCard,
            hwPhysicalPortInPort,
            hwPhysicalPortName}
        STATUS current
        DESCRIPTION
            "This object indicates that a downstream alarm indication signal is generated on an E1 interface."
        ::= { hwPortNotifications 103 }

    hwE1DownE1AisAlarmResume NOTIFICATION-TYPE
        OBJECTS {
            hwPhysicalPortInSlot,
            hwPhysicalPortInCard,
            hwPhysicalPortInPort,
            hwPhysicalPortName}
        STATUS current
        DESCRIPTION
            "This object indicates that the downstream alarm indication signal generated on an E1 interface is cleared."
        ::= { hwPortNotifications 104 }

    hwCposE1LmfaAlarm NOTIFICATION-TYPE
        OBJECTS {
            hwPhysicalPortInSlot,
            hwPhysicalPortInCard,
            hwPhysicalPortInPort,
            hwPortPhysicalHpIndex,
            hwPortPhysicalLpIndex,
            hwPhysicalPortName}
        STATUS current
        DESCRIPTION
            "This object indicates that an out of multiframe (OOM) alarm is generated on the framed E1 channelized from VC12."
        ::= { hwPortNotifications 111 }

    hwCposE1LmfaAlarmResume NOTIFICATION-TYPE
        OBJECTS {
            hwPhysicalPortInSlot,
            hwPhysicalPortInCard,
            hwPhysicalPortInPort,
            hwPortPhysicalHpIndex,
            hwPortPhysicalLpIndex,
            hwPhysicalPortName}
        STATUS current
        DESCRIPTION
            "This object indicates that the OOM alarm generated on the framed E1 channelized from VC12 is cleared."
        ::= { hwPortNotifications 112 }

    hwLaserShutAlarm NOTIFICATION-TYPE
        OBJECTS {
            hwPhysicalPortInSlot,
            hwPhysicalPortInCard,
            hwPhysicalPortInPort,
            hwPhysicalPortName}
        STATUS current
        DESCRIPTION
            "This object indicates that an alarm is generated when the optical laser on a board is shut down."
        ::= { hwPortNotifications 113 }

    hwLaserShutAlarmResume NOTIFICATION-TYPE
        OBJECTS {
            hwPhysicalPortInSlot,
            hwPhysicalPortInCard,
            hwPhysicalPortInPort,
            hwPhysicalPortName}
        STATUS current
        DESCRIPTION
            "This object indicates that a clear alarm is generated when the optical laser on a board is opened."
        ::= { hwPortNotifications 114 }

    hwLaserAutoShutAlarm NOTIFICATION-TYPE
        OBJECTS {
            hwPhysicalPortInSlot,
            hwPhysicalPortInCard,
            hwPhysicalPortInPort,
            hwPhysicalPortName}
        STATUS current
        DESCRIPTION
            "This object indicates that an alarm is generated when the optical laser is shut down automatically."
        ::= { hwPortNotifications 115 }

    hwLaserAutoShutAlarmResume NOTIFICATION-TYPE
        OBJECTS {
            hwPhysicalPortInSlot,
            hwPhysicalPortInCard,
            hwPhysicalPortInPort,
            hwPhysicalPortName}
        STATUS current
        DESCRIPTION
            "This object indicates that the alarm for the automatic shutdown of the optical laser is cleared."
        ::= { hwPortNotifications 116 }

    hwLoopbackAlarm NOTIFICATION-TYPE
        OBJECTS {
            hwPhysicalPortIfIndex,
            hwPhysicalPortName,
            hwPhysicalLoopbackType}
        STATUS current
        DESCRIPTION
            "This object indicates that an alarm is generated due to an interface loopback."
        ::= { hwPortNotifications 117 }

    hwLoopbackAlarmResume NOTIFICATION-TYPE
        OBJECTS {
            hwPhysicalPortIfIndex,
            hwPhysicalPortName,
            hwPhysicalLoopbackType}
        STATUS current
        DESCRIPTION
            "This object indicates that the alarm for the interface loopback is cleared."
        ::= { hwPortNotifications 118 }

    hwOcdAlarm NOTIFICATION-TYPE
        OBJECTS {
            hwPhysicalPortInSlot,
            hwPhysicalPortInCard,
            hwPhysicalPortInPort,
            hwPhysicalPortName}
        STATUS current
        DESCRIPTION
            "Indicates the alarm is detected."
        ::= { hwPortNotifications 119 }

    hwOcdAlarmResume NOTIFICATION-TYPE
        OBJECTS {
            hwPhysicalPortInSlot,
            hwPhysicalPortInCard,
            hwPhysicalPortInPort,
            hwPhysicalPortName}
        STATUS current
        DESCRIPTION
            "Indicates the alarm is cleared."
        ::= { hwPortNotifications 120 }

    hwLcdAlarm NOTIFICATION-TYPE
        OBJECTS {
            hwPhysicalPortInSlot,
            hwPhysicalPortInCard,
            hwPhysicalPortInPort,
            hwPhysicalPortName}
        STATUS current
        DESCRIPTION
            "This object indicates an alarm for the loss of synchronization codes (SCs)."
        ::= { hwPortNotifications 121 }

    hwLcdAlarmResume NOTIFICATION-TYPE
        OBJECTS {
            hwPhysicalPortInSlot,
            hwPhysicalPortInCard,
            hwPhysicalPortInPort,
            hwPhysicalPortName}
        STATUS current
        DESCRIPTION
            "This object indicates that the alarm for the loss of synchronization codes (SCs) is cleared."
        ::= { hwPortNotifications 122 }

    hwUhcsAlarm NOTIFICATION-TYPE
        OBJECTS {
            hwPhysicalPortInSlot,
            hwPhysicalPortInCard,
            hwPhysicalPortInPort,
            hwPhysicalPortName}
        STATUS current
        DESCRIPTION
            "Indicates the alarm is detected."
        ::= { hwPortNotifications 123 }

    hwUhcsAlarmResume NOTIFICATION-TYPE
        OBJECTS {
            hwPhysicalPortInSlot,
            hwPhysicalPortInCard,
            hwPhysicalPortInPort,
            hwPhysicalPortName}
        STATUS current
        DESCRIPTION
            "Indicates the alarm is cleared."
        ::= { hwPortNotifications 124 }

    hwChcsAlarm NOTIFICATION-TYPE
        OBJECTS {
            hwPhysicalPortInSlot,
            hwPhysicalPortInCard,
            hwPhysicalPortInPort,
            hwPhysicalPortName}
        STATUS current
        DESCRIPTION
            "Indicates the alarm is detected."
        ::= { hwPortNotifications 125 }

    hwChcsAlarmResume NOTIFICATION-TYPE
        OBJECTS {
            hwPhysicalPortInSlot,
            hwPhysicalPortInCard,
            hwPhysicalPortInPort,
            hwPhysicalPortName}
        STATUS current
        DESCRIPTION
            "Indicates the alarm is cleared."
        ::= { hwPortNotifications 126 }

    hwChannelLoopbackAlarm NOTIFICATION-TYPE
        OBJECTS {
            hwSDHHpPerfCurrentIfIndex,
            hwSDHLpPerfCurrentIfIndex,
            hwPhysicalLoopbackType,
            hwPhysicalPortIfIndex,
            hwPhysicalPortName}
        STATUS current
        DESCRIPTION
            "Indicates the alarm is detected."
        ::= { hwPortNotifications 127 }

    hwChannelLoopbackAlarmResume NOTIFICATION-TYPE
        OBJECTS {
            hwSDHHpPerfCurrentIfIndex,
            hwSDHLpPerfCurrentIfIndex,
            hwPhysicalLoopbackType,
            hwPhysicalPortIfIndex,
            hwPhysicalPortName}
        STATUS current
        DESCRIPTION
            "Indicates the alarm is cleared."
        ::= { hwPortNotifications 128 }

    hwCesLopsAlarm NOTIFICATION-TYPE
        OBJECTS {
            hwPWCesVcID,
            hwPWCesVcType,
            hwPeerIpAddr,
            hwPWPortName}
        STATUS current
        DESCRIPTION
            "Indicates the alarm is detected."
        ::= { hwPortNotifications 129 }

    hwCesLopsAlarmResume NOTIFICATION-TYPE
        OBJECTS {
            hwPWCesVcID,
            hwPWCesVcType,
            hwPeerIpAddr,
            hwPWPortName}
        STATUS current
        DESCRIPTION
            "Indicates the alarm is cleared."
        ::= { hwPortNotifications 130 }

    hwAtmPwLosPktExcAlarm NOTIFICATION-TYPE
        OBJECTS {
            hwAtmVcID,
            hwAtmVcType,
            hwAtmPeerIpAddr,
            hwAtmPWPortName}
        STATUS current
        DESCRIPTION
            "Indicates the alarm is detected."
        ::= { hwPortNotifications 131 }

    hwAtmPwLosPktExcAlarmResume NOTIFICATION-TYPE
        OBJECTS {
            hwAtmVcID,
            hwAtmVcType,
            hwAtmPeerIpAddr,
            hwAtmPWPortName}
        STATUS current
        DESCRIPTION
            "Indicates the alarm is cleared."
        ::= { hwPortNotifications 132 }

    hwAtmPwMisorderPktExcAlarm NOTIFICATION-TYPE
        OBJECTS {
            hwAtmVcID,
            hwAtmVcType,
            hwAtmPeerIpAddr,
            hwAtmPWPortName}
        STATUS current
        DESCRIPTION
            "Indicates the alarm is detected."
        ::= { hwPortNotifications 133 }

    hwAtmPwMisorderPktExcAlarmResume NOTIFICATION-TYPE
        OBJECTS {
            hwAtmVcID,
            hwAtmVcType,
            hwAtmPeerIpAddr,
            hwAtmPWPortName}
        STATUS current
        DESCRIPTION
            "Indicates the alarm is cleared."
        ::= { hwPortNotifications 134 }

    hwAtmPwUnknownCellExcAlarm NOTIFICATION-TYPE
        OBJECTS {
            hwAtmVcID,
            hwAtmVcType,
            hwAtmPeerIpAddr,
            hwAtmPWPortName}
        STATUS current
        DESCRIPTION
            "Indicates the alarm is detected."
        ::= { hwPortNotifications 135 }

    hwAtmPwUnknownCellExcAlarmResume NOTIFICATION-TYPE
        OBJECTS {
            hwAtmVcID,
            hwAtmVcType,
            hwAtmPeerIpAddr,
            hwAtmPWPortName}
        STATUS current
        DESCRIPTION
            "Indicates the alarm is cleared."
        ::= { hwPortNotifications 136 }

    hwInputErrorAlarm NOTIFICATION-TYPE
        OBJECTS {
            hwPhysicalPortInSlot,
            hwPhysicalPortInCard,
            hwPhysicalPortInPort,
            hwPhysicalPortName}
        STATUS current
        DESCRIPTION
            "This object indicates that an alarm is generated when the number of input errors on an interface exceeds the upper threshold."
        ::= { hwPortNotifications 153 }

    hwInputErrorAlarmResume NOTIFICATION-TYPE
        OBJECTS {
            hwPhysicalPortInSlot,
            hwPhysicalPortInCard,
            hwPhysicalPortInPort,
            hwPhysicalPortName}
        STATUS current
        DESCRIPTION
            "This object indicates that a clear alarm is generated when the number of input errors on an interface falls below the upper threshold."
        ::= { hwPortNotifications 154 }

    hwOutputErrorAlarm NOTIFICATION-TYPE
        OBJECTS {
            hwPhysicalPortInSlot,
            hwPhysicalPortInCard,
            hwPhysicalPortInPort,
            hwPhysicalPortName}
        STATUS current
        DESCRIPTION
            "This object indicates that an alarm is generated when the number of output errors on an interface exceeds the upper threshold."
        ::= { hwPortNotifications 155 }

    hwOutputErrorAlarmResume NOTIFICATION-TYPE
        OBJECTS {
            hwPhysicalPortInSlot,
            hwPhysicalPortInCard,
            hwPhysicalPortInPort,
            hwPhysicalPortName}
        STATUS current
        DESCRIPTION
            "This object indicates that a clear alarm is generated when the number of output errors on an interface falls below the upper threshold."
        ::= { hwPortNotifications 156 }

    hwPortAlarmTraps OBJECT IDENTIFIER ::= { hwPortNotifications 157 }

    hwPhysicalPortCrcError NOTIFICATION-TYPE
        OBJECTS {
            hwPhysicalPortThrIfIndex,
            hwPhysicalPortThrName,
            hwPhysicalPortCrcErrorStatistics,
            hwPhysicalPortCrcErrorHighThreshold,
            hwPhysicalPortCrcErrorLowThreshold,
            hwPhysicalPortCrcErrorInterval}
        STATUS current
        DESCRIPTION
            "Port Crc error alarm notification."
        ::= { hwPortAlarmTraps 1 }

    hwPhysicalPortCrcErrorResume NOTIFICATION-TYPE
        OBJECTS {
            hwPhysicalPortThrIfIndex,
            hwPhysicalPortThrName,
            hwPhysicalPortCrcErrorStatistics,
            hwPhysicalPortCrcErrorHighThreshold,
            hwPhysicalPortCrcErrorLowThreshold,
            hwPhysicalPortCrcErrorInterval}
        STATUS current
        DESCRIPTION
            "Port Crc error alarm resume."
        ::= { hwPortAlarmTraps 2 }

    hwPhysicalPortSymbolError NOTIFICATION-TYPE
        OBJECTS {
            hwPhysicalPortThrIfIndex,
            hwPhysicalPortThrName,
            hwPhysicalPortSymbolErrorStatistics,
            hwPhysicalPortSymbolErrorHighThreshold,
            hwPhysicalPortSymbolErrorLowThreshold,
            hwPhysicalPortSymbolErrorInterval}
        STATUS current
        DESCRIPTION
            "This object indicates the Symbol error alarm."
        ::= { hwPortAlarmTraps 3 }

    hwPhysicalPortSymbolErrorResume NOTIFICATION-TYPE
        OBJECTS {
            hwPhysicalPortThrIfIndex,
            hwPhysicalPortThrName,
            hwPhysicalPortSymbolErrorStatistics,
            hwPhysicalPortSymbolErrorHighThreshold,
            hwPhysicalPortSymbolErrorLowThreshold,
            hwPhysicalPortSymbolErrorInterval}
        STATUS current
        DESCRIPTION
            "This object indicates that the Symbol error alarm is cleared."
        ::= { hwPortAlarmTraps 4 }

    hwPhysicalPortSdhError NOTIFICATION-TYPE
        OBJECTS {
            hwPhysicalPortThrIfIndex,
            hwPhysicalPortThrName,
            hwPhysicalPortSdhErrorStatistics,
            hwPhysicalPortSdhErrorHighThreshold,
            hwPhysicalPortSdhErrorLowThreshold,
            hwPhysicalPortSdhErrorInterval}
        STATUS current
        DESCRIPTION
            "This object indicates the Input error alarm."
        ::= { hwPortAlarmTraps 5 }

    hwPhysicalPortSdhErrorResume NOTIFICATION-TYPE
        OBJECTS {
            hwPhysicalPortThrIfIndex,
            hwPhysicalPortThrName,
            hwPhysicalPortSdhErrorStatistics,
            hwPhysicalPortSdhErrorHighThreshold,
            hwPhysicalPortSdhErrorLowThreshold,
            hwPhysicalPortSdhErrorInterval}
        STATUS current
        DESCRIPTION
            "This object indicates that the Input error alarm is cleared."
        ::= { hwPortAlarmTraps 6 }

    hwPhysicalPortBip8SdError NOTIFICATION-TYPE
        OBJECTS {
            hwPhysicalPortThrIfIndex,
            hwPhysicalPortThrName,
            hwPhysicalPortBIP8SDErrorThreshold}
        STATUS current
        DESCRIPTION
            "This object indicates the Output error alarm."
        ::= { hwPortAlarmTraps 7 }

    hwPhysicalPortBip8SdErrorResume NOTIFICATION-TYPE
        OBJECTS {
            hwPhysicalPortThrIfIndex,
            hwPhysicalPortThrName,
            hwPhysicalPortBIP8SDErrorThreshold}
        STATUS current
        DESCRIPTION
            "This object indicates that the Output error alarm is cleared."
        ::= { hwPortAlarmTraps 8 }

    hwPhysicalPortCrcPacketErrorRatio NOTIFICATION-TYPE
        OBJECTS {
            hwPhysicalPortThrIfIndex,
            hwPhysicalPortThrName,
            hwPhysicalPortCrcPerCurrentValueString,
            hwPhysicalPortCrcPerAlarmThresholdString,
            hwPhysicalPortCrcPerResumeThresholdString}
        STATUS current
        DESCRIPTION
            "This object indicates that an alarm is generated when the number of CRC errors on a physical interface exceeds the upper threshold. The host sends a trap message to the NMS."
        ::= { hwPortAlarmTraps 9 }

    hwPhysicalPortCrcPacketErrorRatioResume NOTIFICATION-TYPE
        OBJECTS {
            hwPhysicalPortThrIfIndex,
            hwPhysicalPortThrName,
            hwPhysicalPortCrcPerCurrentValueString,
            hwPhysicalPortCrcPerAlarmThresholdString,
            hwPhysicalPortCrcPerResumeThresholdString}
        STATUS current
        DESCRIPTION
            "This object indicates that a clear alarm is generated when the number of CRC errors on a physical interface falls below the upper threshold. The host sends a trap message to the NMS."
        ::= { hwPortAlarmTraps 10 }

    hwPhysicalPortCrcSd NOTIFICATION-TYPE
        OBJECTS {
            hwPhysicalPortThrIfIndex,
            hwPhysicalPortThrName,
            hwPhysicalPortCrcPerCurrentValueString,
            hwPhysicalPortCrcSdAlarmThresholdString,
            hwPhysicalPortCrcSdResumeThresholdString}
        STATUS current
        DESCRIPTION
            "Port MAC_FCS_SD alarm notification."
        ::= { hwPortAlarmTraps 11 }

    hwPhysicalPortCrcSdResume NOTIFICATION-TYPE
        OBJECTS {
            hwPhysicalPortThrIfIndex,
            hwPhysicalPortThrName,
            hwPhysicalPortCrcPerCurrentValueString,
            hwPhysicalPortCrcSdAlarmThresholdString,
            hwPhysicalPortCrcSdResumeThresholdString}
        STATUS current
        DESCRIPTION
            "Port MAC_FCS_SD alarm resume."
        ::= { hwPortAlarmTraps 12 }

    hwPhysicalPortCrcExc NOTIFICATION-TYPE
        OBJECTS {
            hwPhysicalPortThrIfIndex,
            hwPhysicalPortThrName,
            hwPhysicalPortCrcPerCurrentValueString,
            hwPhysicalPortCrcExcAlarmThresholdString,
            hwPhysicalPortCrcExcResumeThresholdString}
        STATUS current
        DESCRIPTION
            "Port MAC_FCS_EXC alarm notification."
        ::= { hwPortAlarmTraps 13 }

    hwPhysicalPortCrcExcResume NOTIFICATION-TYPE
        OBJECTS {
            hwPhysicalPortThrIfIndex,
            hwPhysicalPortThrName,
            hwPhysicalPortCrcPerCurrentValueString,
            hwPhysicalPortCrcExcAlarmThresholdString,
            hwPhysicalPortCrcExcResumeThresholdString}
        STATUS current
        DESCRIPTION
            "Port MAC_FCS_EXC alarm resume notification."
        ::= { hwPortAlarmTraps 14 }

    hwPhysicalPortCrcPerWarning NOTIFICATION-TYPE
        OBJECTS {
            hwPhysicalPortThrIfIndex,
            hwPhysicalPortThrName,
            hwPhysicalPortCrcPerCurrentValueString,
            hwPhysicalPortCrcPerWarningThresholdString,
            hwPhysicalPortCrcPerWarningResumeThresholdString}
        STATUS current
        DESCRIPTION
            "Port CRC-PER(Packet Error Ratio) warning notification."
        ::= { hwPortAlarmTraps 15 }

    hwPhysicalPortCrcPerWarningResume NOTIFICATION-TYPE
        OBJECTS {
            hwPhysicalPortThrIfIndex,
            hwPhysicalPortThrName,
            hwPhysicalPortCrcPerCurrentValueString,
            hwPhysicalPortCrcPerWarningThresholdString,
            hwPhysicalPortCrcPerWarningResumeThresholdString}
        STATUS current
        DESCRIPTION
            "Port CRC-PER(Packet Error Ratio) warning resume notification."
        ::= { hwPortAlarmTraps 16 }

    hwPhysicalPortFlowSurge OBJECT IDENTIFIER ::= { hwPortAlarmTraps 17 }

    hwInputBroadcastSurgeOccur NOTIFICATION-TYPE
        OBJECTS { hwPhysicalPortIfIndex, hwPhysicalPortName }
        STATUS current
        DESCRIPTION
            "Input broadcast surge occurred."
        ::= { hwPhysicalPortFlowSurge 1 }

    hwInputBroadcastSurgeResume NOTIFICATION-TYPE
        OBJECTS { hwPhysicalPortIfIndex, hwPhysicalPortName }
        STATUS current
        DESCRIPTION
            "Input broadcast surge resumed."
        ::= { hwPhysicalPortFlowSurge 2 }

    hwOutputBroadcastSurgeOccur NOTIFICATION-TYPE
        OBJECTS { hwPhysicalPortIfIndex, hwPhysicalPortName }
        STATUS current
        DESCRIPTION
            "Output broadcast surge occurred."
        ::= { hwPhysicalPortFlowSurge 3 }

    hwOutputBroadcastSurgeResume NOTIFICATION-TYPE
        OBJECTS { hwPhysicalPortIfIndex, hwPhysicalPortName }
        STATUS current
        DESCRIPTION
            "Output broadcast surge resumed."
        ::= { hwPhysicalPortFlowSurge 4 }
        
    hwPortCrcRateExceed NOTIFICATION-TYPE
        OBJECTS {
            hwPhysicalPortThrIfIndex,
            hwPhysicalPortThrName,
            hwPhysicalPortCrcPerCurrentValueString,
            hwPhysicalPortCrcPerAlarmThresholdString}
        STATUS current
        DESCRIPTION
            "Indicates that the rate of the incoming traffic packets with CRC error exceeds the alarm threshold."
        ::= { hwPortAlarmTraps 18 }

    hwPortErrorRateExceed NOTIFICATION-TYPE
        OBJECTS {
            hwPhysicalPortThrIfIndex,
            hwPhysicalPortThrName,
            hwPhysicalPortErrorPerCurrentValueString,
            hwPhysicalPortErrorPerAlarmThresholdString}
        STATUS current
        DESCRIPTION
            "Indicates that the rate of the incoming traffic error packets exceeds the alarm threshold."
        ::= { hwPortAlarmTraps 19 }
	
	hwPhysicalPortInBroadcastRapidChange NOTIFICATION-TYPE
	OBJECTS {
		hwPhysicalPortThrIfIndex,
		hwPhysicalPortThrName,
		hwInputBroadcastChangeThreshold,
		hwCurrentStatisticalInputBroadcast,
		hwBaseStatisticalInputBroadcast}
	STATUS current
	DESCRIPTION
		"Indicates that the rate of the input broadcast exceeds the threshold."
	::= { hwPortAlarmTraps 20 }
	
    hwLoopBackAutoClearNotice NOTIFICATION-TYPE
        OBJECTS {
            hwPhysicalPortIfIndex,
            hwPhysicalPortName}
        STATUS current
        DESCRIPTION
            "set port undo loopback while set loopback autoclear enable when time out."
        ::= { hwPortNotifications 160 }

    hwChannelLoopBackAutoClearNotice NOTIFICATION-TYPE
        OBJECTS {
            hwPhysicalPortIfIndex,
            hwPhysicalPortName,
            hwDs1ChannelId}
        STATUS current
        DESCRIPTION
            "set channel undo loopback while set loopback autoclear enable when time out."
        ::= { hwPortNotifications 161 }

    hwHpJ1TiuAlarm NOTIFICATION-TYPE
        OBJECTS {
            hwPhysicalPortInSlot,
            hwPhysicalPortInCard,
            hwPhysicalPortInPort,
            hwPortPhysicalHpIndex,
            hwPhysicalPortName}
        STATUS current
        DESCRIPTION
            "This object indicates that an alarm is generated when the higher order path (HP) trace identifier is unstable."
        ::= { hwPortNotifications 162 }

    hwHpJ1TiuAlarmResume NOTIFICATION-TYPE
        OBJECTS {
            hwPhysicalPortInSlot,
            hwPhysicalPortInCard,
            hwPhysicalPortInPort,
            hwPortPhysicalHpIndex,
            hwPhysicalPortName}
        STATUS current
        DESCRIPTION
            "This object indicates that a clear alarm is generated when the higher order path (HP) trace identifier becomes stable."
        ::= { hwPortNotifications 163 }

    hwPortAlarmInverseAutoRecover NOTIFICATION-TYPE
        OBJECTS {
            hwPhysicalPortName}
        STATUS current
        DESCRIPTION
            "Port alarm inverse auto recover."
        ::= { hwPortNotifications 164 }

    hwB1ExcAlarm NOTIFICATION-TYPE
        OBJECTS {
            hwPhysicalPortInSlot,
            hwPhysicalPortInCard,
            hwPhysicalPortInPort,
            hwPhysicalPortName}
        STATUS current
        DESCRIPTION
            "This object indicates that an alarm is generated when the number of B1 errors exceeds a specified threshold."
        ::= { hwPortNotifications 165 }

    hwB1ExcAlarmResume NOTIFICATION-TYPE
        OBJECTS {
            hwPhysicalPortInSlot,
            hwPhysicalPortInCard,
            hwPhysicalPortInPort,
            hwPhysicalPortName}
        STATUS current
        DESCRIPTION
            "This object indicates that a clear alarm is generated when the number of B1 errors falls below a specified threshold."
        ::= { hwPortNotifications 166 }

    hwB3ExcAlarm NOTIFICATION-TYPE
        OBJECTS {
            hwPhysicalPortInSlot,
            hwPhysicalPortInCard,
            hwPhysicalPortInPort,
            hwPortPhysicalHpIndex,
            hwPhysicalPortName}
        STATUS current
        DESCRIPTION
            "This object indicates that an alarm is generated when the number of B3 errors exceeds a specified threshold."
        ::= { hwPortNotifications 167 }

    hwB3ExcAlarmResume NOTIFICATION-TYPE
        OBJECTS {
            hwPhysicalPortInSlot,
            hwPhysicalPortInCard,
            hwPhysicalPortInPort,
            hwPortPhysicalHpIndex,
            hwPhysicalPortName}
        STATUS current
        DESCRIPTION
            "This object indicates that a clear alarm is generated when the number of B3 errors falls below a specified threshold."
        ::= { hwPortNotifications 168 }

    hwBip2ExcAlarm NOTIFICATION-TYPE
        OBJECTS {
            hwPhysicalPortInSlot,
            hwPhysicalPortInCard,
            hwPhysicalPortInPort,
            hwPortPhysicalHpIndex,
            hwPortPhysicalLpIndex,
            hwPhysicalPortName}
        STATUS current
        DESCRIPTION
            "This object indicates that an alarm is generated when the number of BIP2 errors exceeds a specified threshold."
        ::= { hwPortNotifications 169 }

    hwBip2ExcAlarmResume NOTIFICATION-TYPE
        OBJECTS {
            hwPhysicalPortInSlot,
            hwPhysicalPortInCard,
            hwPhysicalPortInPort,
            hwPortPhysicalHpIndex,
            hwPortPhysicalLpIndex,
            hwPhysicalPortName}
        STATUS current
        DESCRIPTION
            "This object indicates that a clear alarm is generated when the number of BIP2 errors falls below a specified threshold."
        ::= { hwPortNotifications 170 }

    hwLicenseLimitAlarm NOTIFICATION-TYPE
        OBJECTS {
            hwPhysicalPortInSlot,
            hwPhysicalPortInCard,
            hwPhysicalPortInPort,
            hwPhysicalPortName}
        STATUS current
        DESCRIPTION
            "Indicates the alarm is detected."
        ::= { hwPortNotifications 171 }

    hwLicenseLimitAlarmResume NOTIFICATION-TYPE
        OBJECTS {
            hwPhysicalPortInSlot,
            hwPhysicalPortInCard,
            hwPhysicalPortInPort,
            hwPhysicalPortName}
        STATUS current
        DESCRIPTION
            "Indicates the alarm is cleared."
        ::= { hwPortNotifications 172 }

    hwOpticalModuleIsNotAuthorized NOTIFICATION-TYPE
        OBJECTS {
            hwPhysicalPortThrIfIndex,
            hwPhysicalPortThrName}
        STATUS current
        DESCRIPTION
            "This object indicates that an alarm is generated when the inserted optical module is one not authenticated by Huawei."
        ::= { hwPortNotifications 173 }

    hwOpticalModuleIsNotAuthorizedResume NOTIFICATION-TYPE
        OBJECTS {
            hwPhysicalPortThrIfIndex,
            hwPhysicalPortThrName}
        STATUS current
        DESCRIPTION
            "This object indicates that a clear alarm is generated when the non-Huawei-authenticated optical module is removed."
        ::= { hwPortNotifications 174 }

    hwLocalFaultAlarm NOTIFICATION-TYPE
        OBJECTS {
            hwPhysicalPortIfIndex,
            hwPhysicalPortName}
        STATUS current
        DESCRIPTION
            "This object indicates that an alarm is generated when the receive link from the remote device to the local device fails."
        ::= { hwPortNotifications 175 }

    hwLocalFaultAlarmResume NOTIFICATION-TYPE
        OBJECTS {
            hwPhysicalPortIfIndex,
            hwPhysicalPortName}
        STATUS current
        DESCRIPTION
            "This object indicates that a clear alarm is generated when the receive link from the remote device to the local device recovers."
        ::= { hwPortNotifications 176 }

    hwRemoteFaultAlarm NOTIFICATION-TYPE
        OBJECTS {
            hwPhysicalPortIfIndex,
            hwPhysicalPortName}
        STATUS current
        DESCRIPTION
            "This object indicates that an alarm is generated when the transmit link from the remote device to the local device fails."
        ::= { hwPortNotifications 177 }

    hwRemoteFaultAlarmResume NOTIFICATION-TYPE
        OBJECTS {
            hwPhysicalPortIfIndex,
            hwPhysicalPortName}
        STATUS current
        DESCRIPTION
            "This object indicates that a clear alarm is generated when the transmit link from the remote device to the local device recovers."
        ::= { hwPortNotifications 178 }

    hwCopperPolarityError NOTIFICATION-TYPE
        OBJECTS {
            hwPhysicalPortIfIndex,
            hwPhysicalPortName}
        STATUS current
        DESCRIPTION
            "This object indicates that an alarm is generated when a polarity error occurs on an electrical interface."
        ::= { hwPortNotifications 179 }

    hwCopperPolarityErrorResume NOTIFICATION-TYPE
        OBJECTS {
            hwPhysicalPortIfIndex,
            hwPhysicalPortName}
        STATUS current
        DESCRIPTION
            "This object indicates that a clear alarm is generated when the polarity error on an electrical interface is cleared."
        ::= { hwPortNotifications 180 }

    hwLotuaisAlarm NOTIFICATION-TYPE
        OBJECTS {
            hwPhysicalPortInSlot,
            hwPhysicalPortInCard,
            hwPhysicalPortInPort,
            hwPhysicalPortName}
        STATUS current
        DESCRIPTION
            "Indicates the alarm is detected."
        ::= { hwPortNotifications 181 }

    hwLotuaisAlarmResume NOTIFICATION-TYPE
        OBJECTS {
            hwPhysicalPortInSlot,
            hwPhysicalPortInCard,
            hwPhysicalPortInPort,
            hwPhysicalPortName}
        STATUS current
        DESCRIPTION
            "Indicates the alarm is cleared."
        ::= { hwPortNotifications 182 }

    hwLotulomAlarm NOTIFICATION-TYPE
        OBJECTS {
            hwPhysicalPortInSlot,
            hwPhysicalPortInCard,
            hwPhysicalPortInPort,
            hwPhysicalPortName}
        STATUS current
        DESCRIPTION
            "Indicates the alarm is detected."
        ::= { hwPortNotifications 183 }

    hwLotulomAlarmResume NOTIFICATION-TYPE
        OBJECTS {
            hwPhysicalPortInSlot,
            hwPhysicalPortInCard,
            hwPhysicalPortInPort,
            hwPhysicalPortName}
        STATUS current
        DESCRIPTION
            "Indicates the alarm is cleared."
        ::= { hwPortNotifications 184 }

    hwLotusdberAlarm NOTIFICATION-TYPE
        OBJECTS {
            hwPhysicalPortInSlot,
            hwPhysicalPortInCard,
            hwPhysicalPortInPort,
            hwPhysicalPortName}
        STATUS current
        DESCRIPTION
            "Indicates the alarm is detected."
        ::= { hwPortNotifications 185 }

    hwLotusdberAlarmResume NOTIFICATION-TYPE
        OBJECTS {
            hwPhysicalPortInSlot,
            hwPhysicalPortInCard,
            hwPhysicalPortInPort,
            hwPhysicalPortName}
        STATUS current
        DESCRIPTION
            "Indicates the alarm is cleared."
        ::= { hwPortNotifications 186 }

    hwLotusfberAlarm NOTIFICATION-TYPE
        OBJECTS {
            hwPhysicalPortInSlot,
            hwPhysicalPortInCard,
            hwPhysicalPortInPort,
            hwPhysicalPortName}
        STATUS current
        DESCRIPTION
            "Indicates the alarm is detected."
        ::= { hwPortNotifications 187 }

    hwLotusfberAlarmResume NOTIFICATION-TYPE
        OBJECTS {
            hwPhysicalPortInSlot,
            hwPhysicalPortInCard,
            hwPhysicalPortInPort,
            hwPhysicalPortName}
        STATUS current
        DESCRIPTION
            "Indicates the alarm is cleared."
        ::= { hwPortNotifications 188 }

    hwLoduaisAlarm NOTIFICATION-TYPE
        OBJECTS {
            hwPhysicalPortInSlot,
            hwPhysicalPortInCard,
            hwPhysicalPortInPort,
            hwPhysicalPortName}
        STATUS current
        DESCRIPTION
            "Indicates the alarm is detected."
        ::= { hwPortNotifications 189 }

    hwLoduaisAlarmResume NOTIFICATION-TYPE
        OBJECTS {
            hwPhysicalPortInSlot,
            hwPhysicalPortInCard,
            hwPhysicalPortInPort,
            hwPhysicalPortName}
        STATUS current
        DESCRIPTION
            "Indicates the alarm is cleared."
        ::= { hwPortNotifications 190 }

    hwLodulckAlarm NOTIFICATION-TYPE
        OBJECTS {
            hwPhysicalPortInSlot,
            hwPhysicalPortInCard,
            hwPhysicalPortInPort,
            hwPhysicalPortName}
        STATUS current
        DESCRIPTION
            "Indicates the alarm is detected."
        ::= { hwPortNotifications 191 }

    hwLodulckAlarmResume NOTIFICATION-TYPE
        OBJECTS {
            hwPhysicalPortInSlot,
            hwPhysicalPortInCard,
            hwPhysicalPortInPort,
            hwPhysicalPortName}
        STATUS current
        DESCRIPTION
            "Indicates the alarm is cleared."
        ::= { hwPortNotifications 192 }

    hwLoduociAlarm NOTIFICATION-TYPE
        OBJECTS {
            hwPhysicalPortInSlot,
            hwPhysicalPortInCard,
            hwPhysicalPortInPort,
            hwPhysicalPortName}
        STATUS current
        DESCRIPTION
            "Indicates the alarm is detected."
        ::= { hwPortNotifications 193 }

    hwLoduociAlarmResume NOTIFICATION-TYPE
        OBJECTS {
            hwPhysicalPortInSlot,
            hwPhysicalPortInCard,
            hwPhysicalPortInPort,
            hwPhysicalPortName}
        STATUS current
        DESCRIPTION
            "Indicates the alarm is cleared."
        ::= { hwPortNotifications 194 }

    hwLpmbdiAlarm NOTIFICATION-TYPE
        OBJECTS {
            hwPhysicalPortInSlot,
            hwPhysicalPortInCard,
            hwPhysicalPortInPort,
            hwPhysicalPortName}
        STATUS current
        DESCRIPTION
            "Indicates the alarm is detected."
        ::= { hwPortNotifications 195 }

    hwLpmbdiAlarmResume NOTIFICATION-TYPE
        OBJECTS {
            hwPhysicalPortInSlot,
            hwPhysicalPortInCard,
            hwPhysicalPortInPort,
            hwPhysicalPortName}
        STATUS current
        DESCRIPTION
            "Indicates the alarm is cleared."
        ::= { hwPortNotifications 196 }

    hwLpmtimAlarm NOTIFICATION-TYPE
        OBJECTS {
            hwPhysicalPortInSlot,
            hwPhysicalPortInCard,
            hwPhysicalPortInPort,
            hwPhysicalPortName}
        STATUS current
        DESCRIPTION
            "Indicates the alarm is detected."
        ::= { hwPortNotifications 197 }

    hwLpmtimAlarmResume NOTIFICATION-TYPE
        OBJECTS {
            hwPhysicalPortInSlot,
            hwPhysicalPortInCard,
            hwPhysicalPortInPort,
            hwPhysicalPortName}
        STATUS current
        DESCRIPTION
            "Indicates the alarm is cleared."
        ::= { hwPortNotifications 198 }

    hwLsmbdiAlarm NOTIFICATION-TYPE
        OBJECTS {
            hwPhysicalPortInSlot,
            hwPhysicalPortInCard,
            hwPhysicalPortInPort,
            hwPhysicalPortName}
        STATUS current
        DESCRIPTION
            "Indicates the alarm is detected."
        ::= { hwPortNotifications 199 }

    hwLsmbdiAlarmResume NOTIFICATION-TYPE
        OBJECTS {
            hwPhysicalPortInSlot,
            hwPhysicalPortInCard,
            hwPhysicalPortInPort,
            hwPhysicalPortName}
        STATUS current
        DESCRIPTION
            "Indicates the alarm is cleared."
        ::= { hwPortNotifications 200 }

    hwLsmiaeAlarm NOTIFICATION-TYPE
        OBJECTS {
            hwPhysicalPortInSlot,
            hwPhysicalPortInCard,
            hwPhysicalPortInPort,
            hwPhysicalPortName}
        STATUS current
        DESCRIPTION
            "Indicates the alarm is detected."
        ::= { hwPortNotifications 201 }

    hwLsmiaeAlarmResume NOTIFICATION-TYPE
        OBJECTS {
            hwPhysicalPortInSlot,
            hwPhysicalPortInCard,
            hwPhysicalPortInPort,
            hwPhysicalPortName}
        STATUS current
        DESCRIPTION
            "Indicates the alarm is cleared."
        ::= { hwPortNotifications 202 }

    hwLsmtimAlarm NOTIFICATION-TYPE
        OBJECTS {
            hwPhysicalPortInSlot,
            hwPhysicalPortInCard,
            hwPhysicalPortInPort,
            hwPhysicalPortName}
        STATUS current
        DESCRIPTION
            "Indicates the alarm is detected."
        ::= { hwPortNotifications 203 }

    hwLsmtimAlarmResume NOTIFICATION-TYPE
        OBJECTS {
            hwPhysicalPortInSlot,
            hwPhysicalPortInCard,
            hwPhysicalPortInPort,
            hwPhysicalPortName}
        STATUS current
        DESCRIPTION
            "Indicates the alarm is cleared."
        ::= { hwPortNotifications 204 }

     hwNegotiationFailedAlarm NOTIFICATION-TYPE
         OBJECTS { 
             hwPhysicalPortIfIndex, 
             hwPhysicalPortName }
        STATUS current
        DESCRIPTION 
             "Auto-negotiation failure alarm. Possible causes, including the local auto-negotiation configuration with the peer inconsistencies; 
              the local ability is not compatible with the peer; 
              the physical connection of the two sides is unstable. 
              When the alarm occurs, the port can't be up."
               ::= { hwPortNotifications 205 }	
		
      hwNegotiationFailedAlarmResume NOTIFICATION-TYPE
           OBJECTS { 
             hwPhysicalPortIfIndex, 
             hwPhysicalPortName }
           STATUS current
           DESCRIPTION 
           "Auto-negotiation failure alarm resume."
           ::= { hwPortNotifications 206 } 
           
      hwEthHalfDuplex NOTIFICATION-TYPE
           OBJECTS { 
             hwPhysicalPortIfIndex, 
             hwPhysicalPortName }
           STATUS current
           DESCRIPTION 
           "The port works in the half-duplex mode."
           ::= { hwPortNotifications 207 } 
           
      hwEthFullDuplex NOTIFICATION-TYPE
           OBJECTS { 
             hwPhysicalPortIfIndex, 
             hwPhysicalPortName }
           STATUS current
           DESCRIPTION 
           "The half-duplex mode alarm resume."
           ::= { hwPortNotifications 208 }

      hwPhysicalPortAutoDetectFail NOTIFICATION-TYPE
           OBJECTS { 
              hwPhysicalPortIfIndex, 
              hwPhysicalPortName }
            STATUS current
            DESCRIPTION 
                "Interface auto adapter fail alarm notification."
            ::= { hwPortNotifications 209 }
            
        
       hwPhysicalPortAutoDetectSuccess NOTIFICATION-TYPE
           OBJECTS { 
              hwPhysicalPortIfIndex,
              hwPhysicalPortName }
            STATUS current
            DESCRIPTION 
                "Interface auto adapter fail alarm resume notification."
            ::= { hwPortNotifications 210 }     
            
       hwNotSameBoardInTrunk NOTIFICATION-TYPE
           OBJECTS { 
              hwPhysicalPortIfIndex, 
              hwPhysicalPortName }
            STATUS current
            DESCRIPTION 
                "Not same boards in Eth-trunk."
            ::= { hwPortNotifications 211 } 

        -- 1.3.6.1.4.1.2011.5.25.157.2.212
        hwOtnAlarm OBJECT IDENTIFIER ::= { hwPortNotifications 212 }
        
        
        -- 1.3.6.1.4.1.2011.5.25.157.2.212.1
        hwOtuLomAlarm NOTIFICATION-TYPE
                OBJECTS { hwPhysicalPortInSlot, hwPhysicalPortInCard, hwPhysicalPortInPort, hwPhysicalPortName }
                STATUS current
                DESCRIPTION 
                        "This object indicates the OTU indication signal alarm."
                ::= { hwOtnAlarm 1 }

        
        -- 1.3.6.1.4.1.2011.5.25.157.2.212.2
        hwOtuLomAlarmResume NOTIFICATION-TYPE
                OBJECTS { hwPhysicalPortInSlot, hwPhysicalPortInCard, hwPhysicalPortInPort, hwPhysicalPortName }
                STATUS current
                DESCRIPTION 
                        "This object indicates that the OTU indication signal alarm is cleared."
                ::= { hwOtnAlarm 2 }

        
        -- 1.3.6.1.4.1.2011.5.25.157.2.212.3
        hwOtuAisAlarm NOTIFICATION-TYPE
                OBJECTS { hwPhysicalPortInSlot, hwPhysicalPortInCard, hwPhysicalPortInPort, hwPhysicalPortName }
                STATUS current
                DESCRIPTION 
                        "This object indicates the OTU indication signal alarm."
                ::= { hwOtnAlarm 3 }

        
        -- 1.3.6.1.4.1.2011.5.25.157.2.212.4
        hwOtuAisAlarmResume NOTIFICATION-TYPE
                OBJECTS { hwPhysicalPortInSlot, hwPhysicalPortInCard, hwPhysicalPortInPort, hwPhysicalPortName }
                STATUS current
                DESCRIPTION 
                        "This object indicates that the OTU indication signal alarm is cleared."
                ::= { hwOtnAlarm 4 }

        
        -- 1.3.6.1.4.1.2011.5.25.157.2.212.5
        hwOtuSdAlarm NOTIFICATION-TYPE
                OBJECTS { hwPhysicalPortInSlot, hwPhysicalPortInCard, hwPhysicalPortInPort, hwPhysicalPortName }
                STATUS current
                DESCRIPTION 
                        "This object indicates that an alarm is generated for the OTU signal degrade."
                ::= { hwOtnAlarm 5 }

        
        -- 1.3.6.1.4.1.2011.5.25.157.2.212.6
        hwOtuSdAlarmResume NOTIFICATION-TYPE
                OBJECTS { hwPhysicalPortInSlot, hwPhysicalPortInCard, hwPhysicalPortInPort, hwPhysicalPortName }
                STATUS current
                DESCRIPTION 
                        "This object indicates that the alarm for the OTU signal degrade is cleared."
                ::= { hwOtnAlarm 6 }

        
        -- 1.3.6.1.4.1.2011.5.25.157.2.212.7
        hwOtuSfAlarm NOTIFICATION-TYPE
                OBJECTS { hwPhysicalPortInSlot, hwPhysicalPortInCard, hwPhysicalPortInPort, hwPhysicalPortName }
                STATUS current
                DESCRIPTION 
                        "This object indicates that an alarm is generated for the OTU signal failure."
                ::= { hwOtnAlarm 7 }

        
        -- 1.3.6.1.4.1.2011.5.25.157.2.212.8
        hwOtuSfAlarmResume NOTIFICATION-TYPE
                OBJECTS { hwPhysicalPortInSlot, hwPhysicalPortInCard, hwPhysicalPortInPort, hwPhysicalPortName }
                STATUS current
                DESCRIPTION 
                        "This object indicates that the alarm for the OTU signal degrade is cleared."
                ::= { hwOtnAlarm 8 }

        
        -- 1.3.6.1.4.1.2011.5.25.157.2.212.9
        hwSmBdiAlarm NOTIFICATION-TYPE
                OBJECTS { hwPhysicalPortInSlot, hwPhysicalPortInCard, hwPhysicalPortInPort, hwPhysicalPortName }
                STATUS current
                DESCRIPTION 
                        "This object indicates that the backward defect indication (BDI) alarm is generated."
                ::= { hwOtnAlarm 9 }

        
        -- 1.3.6.1.4.1.2011.5.25.157.2.212.10
        hwSmBdiAlarmResume NOTIFICATION-TYPE
                OBJECTS { hwPhysicalPortInSlot, hwPhysicalPortInCard, hwPhysicalPortInPort, hwPhysicalPortName }
                STATUS current
                DESCRIPTION 
                        "This object indicates that the backward defect indication (BDI) alarm is cleared."
                ::= { hwOtnAlarm 10 }

        
        -- 1.3.6.1.4.1.2011.5.25.157.2.212.11
        hwSmIaeAlarm NOTIFICATION-TYPE
                OBJECTS { hwPhysicalPortInSlot, hwPhysicalPortInCard, hwPhysicalPortInPort, hwPhysicalPortName }
                STATUS current
                DESCRIPTION 
                        "This object indicates that an alarm is generated when the ODU frame alignment between the local and remote ends is incorrect."
                ::= { hwOtnAlarm 11 }

        
        -- 1.3.6.1.4.1.2011.5.25.157.2.212.12
        hwSmIaeAlarmResume NOTIFICATION-TYPE
                OBJECTS { hwPhysicalPortInSlot, hwPhysicalPortInCard, hwPhysicalPortInPort, hwPhysicalPortName }
                STATUS current
                DESCRIPTION 
                        "This object indicates that a clear alarm is generated when the ODU frame alignment error between the local and remote ends is corrected."
                ::= { hwOtnAlarm 12 }

        
        -- 1.3.6.1.4.1.2011.5.25.157.2.212.13
        hwSmTimAlarm NOTIFICATION-TYPE
                OBJECTS { hwPhysicalPortInSlot, hwPhysicalPortInCard, hwPhysicalPortInPort, hwPhysicalPortName }
                STATUS current
                DESCRIPTION 
                        "This object indicates that an alarm is generated when TIM trace identifiers between the local and remote ends mismatch."
                ::= { hwOtnAlarm 13 }

        
        -- 1.3.6.1.4.1.2011.5.25.157.2.212.14
        hwSmTimAlarmResume NOTIFICATION-TYPE
                OBJECTS { hwPhysicalPortInSlot, hwPhysicalPortInCard, hwPhysicalPortInPort, hwPhysicalPortName }
                STATUS current
                DESCRIPTION 
                        "This object indicates that a clear alarm is generated when TIM trace identifiers between the local and remote ends match."
                ::= { hwOtnAlarm 14 }

        
        -- 1.3.6.1.4.1.2011.5.25.157.2.212.15
        hwOduAisAlarm NOTIFICATION-TYPE
                OBJECTS { hwPhysicalPortInSlot, hwPhysicalPortInCard, hwPhysicalPortInPort, hwPhysicalPortName }
                STATUS current
                DESCRIPTION 
                        "This object indicates the ODU indication signal alarm."
                ::= { hwOtnAlarm 15 }

        
        -- 1.3.6.1.4.1.2011.5.25.157.2.212.16
        hwOduAisAlarmResume NOTIFICATION-TYPE
                OBJECTS { hwPhysicalPortInSlot, hwPhysicalPortInCard, hwPhysicalPortInPort, hwPhysicalPortName }
                STATUS current
                DESCRIPTION 
                        "This object indicates that the ODU indication signal alarm is cleared."
                ::= { hwOtnAlarm 16 }

        
        -- 1.3.6.1.4.1.2011.5.25.157.2.212.17
        hwOduLokAlarm NOTIFICATION-TYPE
                OBJECTS { hwPhysicalPortInSlot, hwPhysicalPortInCard, hwPhysicalPortInPort, hwPhysicalPortName }
                STATUS current
                DESCRIPTION 
                        "This object indicates the ODU lock defect alarm."
                ::= { hwOtnAlarm 17 }

        
        -- 1.3.6.1.4.1.2011.5.25.157.2.212.18
        hwOduLokAlarmResume NOTIFICATION-TYPE
                OBJECTS { hwPhysicalPortInSlot, hwPhysicalPortInCard, hwPhysicalPortInPort, hwPhysicalPortName }
                STATUS current
                DESCRIPTION 
                        "This object indicates that the ODU lock defect alarm is cleared."
                ::= { hwOtnAlarm 18 }

        
        -- 1.3.6.1.4.1.2011.5.25.157.2.212.19
        hwOduOciAlarm NOTIFICATION-TYPE
                OBJECTS { hwPhysicalPortInSlot, hwPhysicalPortInCard, hwPhysicalPortInPort, hwPhysicalPortName }
                STATUS current
                DESCRIPTION 
                        "This object indicates that the indication defect alarm for the ODU open connection."
                ::= { hwOtnAlarm 19 }

        
        -- 1.3.6.1.4.1.2011.5.25.157.2.212.20
        hwOduOciAlarmResume NOTIFICATION-TYPE
                OBJECTS { hwPhysicalPortInSlot, hwPhysicalPortInCard, hwPhysicalPortInPort, hwPhysicalPortName }
                STATUS current
                DESCRIPTION 
                        "This object indicates that the indication defect alarm for the ODU open connection is cleared."
                ::= { hwOtnAlarm 20 }

        
        -- 1.3.6.1.4.1.2011.5.25.157.2.212.21
        hwPmBdiAlarm NOTIFICATION-TYPE
                OBJECTS { hwPhysicalPortInSlot, hwPhysicalPortInCard, hwPhysicalPortInPort, hwPhysicalPortName }
                STATUS current
                DESCRIPTION 
                        "This object indicates that the backward defect indication (BDI) alarm is generated."
                ::= { hwOtnAlarm 21 }

        
        -- 1.3.6.1.4.1.2011.5.25.157.2.212.22
        hwPmBdiAlarmResume NOTIFICATION-TYPE
                OBJECTS { hwPhysicalPortInSlot, hwPhysicalPortInCard, hwPhysicalPortInPort, hwPhysicalPortName }
                STATUS current
                DESCRIPTION 
                        "This object indicates that the backward defect indication (BDI) alarm is cleared."
                ::= { hwOtnAlarm 22 }

        
        -- 1.3.6.1.4.1.2011.5.25.157.2.212.23
        hwPmTimAlarm NOTIFICATION-TYPE
                OBJECTS { hwPhysicalPortInSlot, hwPhysicalPortInCard, hwPhysicalPortInPort, hwPhysicalPortName }
                STATUS current
                DESCRIPTION 
                        "This object indicates that an alarm is generated when path trace identifiers between the local and remote ends mismatch."
                ::= { hwOtnAlarm 23 }

        
        -- 1.3.6.1.4.1.2011.5.25.157.2.212.24
        hwPmTimAlarmResume NOTIFICATION-TYPE
                OBJECTS { hwPhysicalPortInSlot, hwPhysicalPortInCard, hwPhysicalPortInPort, hwPhysicalPortName }
                STATUS current
                DESCRIPTION 
                        "This object indicates that a clear alarm is generated when path trace identifiers between the local and remote ends match."
                ::= { hwOtnAlarm 24 }

        -- 1.3.6.1.4.1.2011.5.25.157.2.212.25
        hwPrefecTcaAlarm NOTIFICATION-TYPE
                OBJECTS { hwPhysicalPortInSlot, hwPhysicalPortInCard, hwPhysicalPortInPort, hwPhysicalPortName }
                STATUS current
                DESCRIPTION 
                        "This object indicates that an alarm is generated for forward error correction (FEC) bit errors."
                ::= { hwOtnAlarm 25 }

        
        -- 1.3.6.1.4.1.2011.5.25.157.2.212.26
        hwPrefecTcaAlarmResume NOTIFICATION-TYPE
                OBJECTS { hwPhysicalPortInSlot, hwPhysicalPortInCard, hwPhysicalPortInPort, hwPhysicalPortName }
                STATUS current
                DESCRIPTION 
                        "This object indicates that a clear alarm is generated when forward error correction (FEC) bit errors are removed."
                ::= { hwOtnAlarm 26 }
				
	-- 1.3.6.1.4.1.2011.5.25.157.2.213	
	hwE3UpE3AisAlarm NOTIFICATION-TYPE
        OBJECTS {
            hwPhysicalPortInSlot,
            hwPhysicalPortInCard,
            hwPhysicalPortInPort,
            hwPhysicalPortName}
        STATUS current
        DESCRIPTION
            "Indicates the alarm is detected."
        ::= { hwPortNotifications 213 }

	-- 1.3.6.1.4.1.2011.5.25.157.2.214
    hwE3UpE3AisAlarmResume NOTIFICATION-TYPE
        OBJECTS {
            hwPhysicalPortInSlot,
            hwPhysicalPortInCard,
            hwPhysicalPortInPort,
            hwPhysicalPortName}
        STATUS current
        DESCRIPTION
            "Indicates the alarm is cleared."
        ::= { hwPortNotifications 214 }
	
	-- 1.3.6.1.4.1.2011.5.25.157.2.215
	hwE3AlmE3RaiAlarm NOTIFICATION-TYPE
        OBJECTS {
            hwPhysicalPortInSlot,
            hwPhysicalPortInCard,
            hwPhysicalPortInPort,
            hwPhysicalPortName}
        STATUS current
        DESCRIPTION
            "Indicates the alarm is detected."
        ::= { hwPortNotifications 215 }
	
	-- 1.3.6.1.4.1.2011.5.25.157.2.216
    hwE3AlmE3RaiAlarmResume NOTIFICATION-TYPE
        OBJECTS {
            hwPhysicalPortInSlot,
            hwPhysicalPortInCard,
            hwPhysicalPortInPort,
            hwPhysicalPortName}
        STATUS current
        DESCRIPTION
            "Indicates the alarm is cleared."
        ::= { hwPortNotifications 216 }
     
    -- 1.3.6.1.4.1.2011.5.25.157.2.217
    hwMultiServiceOnOneCardAlarm NOTIFICATION-TYPE
           OBJECTS { 
              hwPhysicalPortInSlot,
              hwPhysicalPortInCard}
            STATUS current
            DESCRIPTION 
                "Multiple services be configured on the same chip of the card."
            ::= { hwPortNotifications 217 }  
               
    -- 1.3.6.1.4.1.2011.5.25.157.2.218
    hwMultiServiceOnOneCardAlarmResume NOTIFICATION-TYPE
           OBJECTS { 
              hwPhysicalPortInSlot,
              hwPhysicalPortInCard}
            STATUS current
            DESCRIPTION 
                "There is no multiple services on the same chip of the card."
            ::= { hwPortNotifications 218 }  
               
    -- 1.3.6.1.4.1.2011.5.25.157.2.219
    hwInputRateChangeOverThresholdNotice NOTIFICATION-TYPE
           OBJECTS {   
                hwPhysicalPortName,
		hwInputRateChangeThresholdPercent,
		hwCurrentStatisticalPeriodRate,
		hwLastStatisticalPeriodRate}
            STATUS current
            DESCRIPTION 
                "The input rate change ratio exceeded the threshold."
            ::= { hwPortNotifications 219 } 
               
    -- 1.3.6.1.4.1.2011.5.25.157.2.220
    hwOutputRateChangeOverThresholdNotice NOTIFICATION-TYPE
           OBJECTS { 
                hwPhysicalPortName,
		hwOutputRateChangeThresholdPercent,
		hwCurrentStatisticalPeriodRate,
		hwLastStatisticalPeriodRate}
            STATUS current
            DESCRIPTION 
                "The output rate change ratio exceeded the threshold."
            ::= { hwPortNotifications 220 } 
	    
		-- 1.3.6.1.4.1.2011.5.25.157.2.221
		hwNarrowBandTraps OBJECT IDENTIFIER ::= { hwPortNotifications 221 }

		
		-- 1.3.6.1.4.1.2011.5.25.157.2.221.1
		hwX50LofAlarm NOTIFICATION-TYPE
			OBJECTS { hwPhysicalPortIfIndex, hwPhysicalPortName }
			STATUS current
			DESCRIPTION 
				"X.50 sub-rate out of frame occurred."
			::= { hwNarrowBandTraps 1 }

		
		-- 1.3.6.1.4.1.2011.5.25.157.2.221.2
		hwX50LofAlarmResume NOTIFICATION-TYPE
			OBJECTS { hwPhysicalPortIfIndex, hwPhysicalPortName }
			STATUS current
			DESCRIPTION 
				"X.50 sub-rate out of frame was cleared."
			::= { hwNarrowBandTraps 2 }

		
		-- 1.3.6.1.4.1.2011.5.25.157.2.221.3
		hwX50AbitAlarm NOTIFICATION-TYPE
			OBJECTS { hwPhysicalPortIfIndex, hwPhysicalPortName }
			STATUS current
			DESCRIPTION 
				"X.50 deframing failed on the remote device."
			::= { hwNarrowBandTraps 3 }

		
		-- 1.3.6.1.4.1.2011.5.25.157.2.221.4
		hwX50AbitAlarmResume NOTIFICATION-TYPE
			OBJECTS { hwPhysicalPortIfIndex, hwPhysicalPortName }
			STATUS current
			DESCRIPTION 
				"The X.50 deframing failure was cleared on the remote device."
			::= { hwNarrowBandTraps 4 }

		-- 1.3.6.1.4.1.2011.5.25.157.2.222
		hwLinkHeartbeatDropAlarm NOTIFICATION-TYPE
			OBJECTS { hwLinkHeartbeatIfindex, hwLinkHeartbeatIfName, hwLinkHeartbeatTxInterface, hwLinkHeartbeatRxInterface }
			STATUS current
			DESCRIPTION 
				"Link-heartbeat drop alarm."
			::= { hwPortNotifications 222 }
		
		-- 1.3.6.1.4.1.2011.5.25.157.2.223
		hwLinkHeartbeatDropAlarmResume NOTIFICATION-TYPE
			OBJECTS { hwLinkHeartbeatIfindex, hwLinkHeartbeatIfName, hwLinkHeartbeatTxInterface, hwLinkHeartbeatRxInterface }
			STATUS current
			DESCRIPTION 
				"Link-heartbeat drop alarm resume."
			::= { hwPortNotifications 223 }
		
		-- 1.3.6.1.4.1.2011.5.25.157.2.224
		hwLinkHeartbeatChangeAlarm NOTIFICATION-TYPE
			OBJECTS { hwLinkHeartbeatIfindex, hwLinkHeartbeatIfName, hwLinkHeartbeatTxInterface, hwLinkHeartbeatRxInterface }
			STATUS current
			DESCRIPTION 
				"Link-heartbeat change alarm."
			::= { hwPortNotifications 224 }
		
		-- 1.3.6.1.4.1.2011.5.25.157.2.225
		hwLinkHeartbeatChangeAlarmResume NOTIFICATION-TYPE
			OBJECTS { hwLinkHeartbeatIfindex, hwLinkHeartbeatIfName, hwLinkHeartbeatTxInterface, hwLinkHeartbeatRxInterface }
			STATUS current
			DESCRIPTION 
				"Link-heartbeat change alarm resume."
			::= { hwPortNotifications 225 }
			
    -- 1.3.6.1.4.1.2011.5.25.157.2.226
    hwPortPhysicalRateDegradeAlarm NOTIFICATION-TYPE
           OBJECTS { 
                hwPhysicalPortIfIndex,
		hwPhysicalPortName,
		hwPortPhysicalRate}
            STATUS current
            DESCRIPTION 
                "This object indicates that an alarm is generated when the negotiation rate on an electrical interface falls sharply."
            ::= { hwPortNotifications 226 } 
               
    -- 1.3.6.1.4.1.2011.5.25.157.2.227
    hwPortPhysicalRateDegradeAlarmResume NOTIFICATION-TYPE
           OBJECTS { 
                hwPhysicalPortIfIndex,
		hwPhysicalPortName}
            STATUS current
            DESCRIPTION 
                "This object indicates that a clear alarm is generated when the negotiation rate on an electrical interface stops falling sharply."
            ::= { hwPortNotifications 227 } 	

	-- 1.3.6.1.4.1.2011.5.25.157.2.228
		hwLicenseInactiveAlarm NOTIFICATION-TYPE
			OBJECTS { hwPhysicalPortIfIndex, hwPhysicalPortName, hwLicenseType }
			STATUS current
			DESCRIPTION 
				"The interface license was not activated."
			::= { hwPortNotifications 228 }

		
		-- 1.3.6.1.4.1.2011.5.25.157.2.229
		hwLicenseInactiveAlarmResume NOTIFICATION-TYPE
			OBJECTS { hwPhysicalPortIfIndex, hwPhysicalPortName, hwLicenseType }
			STATUS current
			DESCRIPTION 
				"The interface license inactivation alarm was cleared."
			::= { hwPortNotifications 229 }

		
		-- 1.3.6.1.4.1.2011.5.25.157.2.230
		hwLicenseResourceLackAlarm NOTIFICATION-TYPE
			OBJECTS { hwLicenseType, hwMaxPortNum, hwUsedPortNum }
			STATUS current
			DESCRIPTION 
				"Interfaces of this type in use exceeded the maximum number."
			::= { hwPortNotifications 230 }

		
		-- 1.3.6.1.4.1.2011.5.25.157.2.231
		hwLicenseResourceLackAlarmResume NOTIFICATION-TYPE
			OBJECTS { hwLicenseType, hwMaxPortNum, hwUsedPortNum }
			STATUS current
			DESCRIPTION 
				"The maximum number-crossing alarm was cleared."
			::= { hwPortNotifications 231 }

		-- 1.3.6.1.4.1.2011.5.25.157.2.232
		hwPortModeChangeTrap NOTIFICATION-TYPE
			OBJECTS {
				hwPhysicalPortIfIndex,
				hwPhysicalPortName,
				hwPhysicalPortMode}
			STATUS current
			DESCRIPTION 
				"This object indicates that the port rate type is changed."
			::= { hwPortNotifications 232 }			
    		-- 1.3.6.1.4.1.2011.5.25.157.2.233
	    hwRdiAlarm NOTIFICATION-TYPE
        OBJECTS {hwPhysicalPortIfIndex, hwPhysicalPortName}
        STATUS current
        DESCRIPTION
            "The peer end was faulty."
        ::= { hwPortNotifications 233 }
	
		-- 1.3.6.1.4.1.2011.5.25.157.2.234
	    hwRdiAlarmResume NOTIFICATION-TYPE
        OBJECTS {hwPhysicalPortIfIndex, hwPhysicalPortName}
        STATUS current
        DESCRIPTION
            "The peer end recovered from faults."
        ::= { hwPortNotifications 234 }

		-- 1.3.6.1.4.1.2011.5.25.157.2.235
	    hwAisAlarm NOTIFICATION-TYPE
        OBJECTS {hwPhysicalPortIfIndex, hwPhysicalPortName}
        STATUS current
        DESCRIPTION
            "Upstream signals were abnormal."
        ::= { hwPortNotifications 235 }
	
		-- 1.3.6.1.4.1.2011.5.25.157.2.236
	    hwAisAlarmResume NOTIFICATION-TYPE
        OBJECTS {hwPhysicalPortIfIndex, hwPhysicalPortName}
        STATUS current
        DESCRIPTION
            "Upstream signals recovered."
        ::= { hwPortNotifications 236 }
		
		-- 1.3.6.1.4.1.2011.5.25.157.2.237
	    hwCollisionAlarm NOTIFICATION-TYPE
        OBJECTS {hwPhysicalPortIfIndex, hwScadaGroupId, hwPhysicalPortName}
        STATUS current
        DESCRIPTION
            "The link encountered a collision."
        ::= { hwPortNotifications 237 }
	
		-- 1.3.6.1.4.1.2011.5.25.157.2.238
	    hwCollisionAlarmResume NOTIFICATION-TYPE
        OBJECTS {hwPhysicalPortIfIndex, hwScadaGroupId, hwPhysicalPortName}
        STATUS current
        DESCRIPTION
            "The link recovered from a collision."
        ::= { hwPortNotifications 238 }	
        
		-- 1.3.6.1.4.1.2011.5.25.157.2.239
		hwSubIfNumExceededSpecAlarm NOTIFICATION-TYPE
			OBJECTS { hwSubIfSpecNum }
			STATUS current
			DESCRIPTION 
				"The nunber of sub interface exceeded spec alarm."
			::= { hwPortNotifications 239 }

		
		-- 1.3.6.1.4.1.2011.5.25.157.2.240
		hwSubIfNumExceededSpecAlarmResume NOTIFICATION-TYPE
			OBJECTS { hwSubIfSpecNum }
			STATUS current
			DESCRIPTION 
				"The number of sub interface exceeded spec alarm resume."
			::= { hwPortNotifications 240 }

		hwPortSpeedChangeTrap NOTIFICATION-TYPE
			OBJECTS { hwPhysicalPortIfIndex,hwPhysicalPortName, hwPhysicalPortLastSpeed, hwPhysicalPortCurSpeed }
			STATUS current
			DESCRIPTION 
				"The speed of port is changed."
			::= { hwPortNotifications 241 }

    -- 1.3.6.1.4.1.2011.5.25.157.2.242
    hwPortGroupTransModeDiff NOTIFICATION-TYPE
        OBJECTS { hwPhysicalPortInSlot, hwPhysicalPortInCard, hwPhysicalPortGroupID, hwPortTransModeReasonDescr }
	STATUS current
	DESCRIPTION 
	        "This group of interfaces do not work in the same transmission mode."
	::= { hwPortNotifications 242 }
			
     -- 1.3.6.1.4.1.2011.5.25.157.2.243	
    hwPortGroupTransModeDiffResume NOTIFICATION-TYPE
        OBJECTS { hwPhysicalPortInSlot, hwPhysicalPortInCard, hwPhysicalPortGroupID, hwPortTransModeReasonDescr }
	STATUS current
	DESCRIPTION 
	         "This group of interfaces work in the same transmission mode now."
	::= { hwPortNotifications 243 }	

    -- 1.3.6.1.4.1.2011.5.25.157.2.244
    hwImpedanceMismatch NOTIFICATION-TYPE
    OBJECTS { hwPhysicalPortIfIndex, hwPhysicalPortName }
			STATUS current
			DESCRIPTION 
				"The configured interface impedance value did not match that of the cable."
			::= { hwPortNotifications 244 }
    -- 1.3.6.1.4.1.2011.5.25.157.2.245
    hwPicLcdAlarm NOTIFICATION-TYPE
        OBJECTS { hwPhysicalPortInSlot,
            hwPhysicalPortInCard,
            hwPhysicalPortInPort,
            hwPhysicalPortName}
        STATUS current
        DESCRIPTION
            "Loss of code group synchronization alarm is detected."
        ::= { hwPortNotifications 245 }
    -- 1.3.6.1.4.1.2011.5.25.157.2.246
    hwPicLcdAlarmResume NOTIFICATION-TYPE
        OBJECTS {hwPhysicalPortInSlot,
            hwPhysicalPortInCard,
            hwPhysicalPortInPort,
            hwPhysicalPortName}
        STATUS current
        DESCRIPTION
            "Loss of code group synchronization alarm  is cleared."
        ::= { hwPortNotifications 246 }
		
		-- 1.3.6.1.4.1.2011.5.25.157.2.247
		hwBoardNotSupportAssignTrunk NOTIFICATION-TYPE
			OBJECTS { entPhysicalName }
			STATUS current
			DESCRIPTION 
				"The card does not support extensions of Eth-Trunk specifications."
			::= { hwPortNotifications 247 }
     -- 1.3.6.1.4.1.2011.5.25.157.2.248	
    hwPortProtectGroupUnavailable NOTIFICATION-TYPE
        OBJECTS { hwPortProtectGroupId }
	STATUS current
	DESCRIPTION 
	        "The port protection group is unavailable."
	::= { hwPortNotifications 248 }
			
     -- 1.3.6.1.4.1.2011.5.25.157.2.249
    hwPortProtectGroupAvailable NOTIFICATION-TYPE          
        OBJECTS { hwPortProtectGroupId }
	STATUS current
	DESCRIPTION 
	         "The port protection group is available."
	::= { hwPortNotifications 249 }	
	
	 -- 1.3.6.1.4.1.2011.5.25.157.2.250
	hwPortProtectGroupDelete NOTIFICATION-TYPE          
        OBJECTS { hwPortProtectGroupId }
	STATUS current
	DESCRIPTION 
	         "The port protection group was deleted."
	::= { hwPortNotifications 250 }	
	-- 1.3.6.1.4.1.2011.5.25.157.2.251
		hwDelayOverConfig NOTIFICATION-TYPE
			OBJECTS { hwPhysicalPortIfIndex, hwPhysicalPortName }
			STATUS current
			DESCRIPTION 
				"Real-time E2E Delay Exceeded the Configured Delay."
			::= { hwPortNotifications 251 }

		
		-- 1.3.6.1.4.1.2011.5.25.157.2.252
		hwDelayOverConfigResume NOTIFICATION-TYPE
			OBJECTS { hwPhysicalPortIfIndex, hwPhysicalPortName }
			STATUS current
			DESCRIPTION 
				"Alarm Indicating the Real-time E2E Delay Exceeded the Configured Delay Was Cleared."
			::= { hwPortNotifications 252 }
		-- 1.3.6.1.4.1.2011.5.25.157.2.253
		hwAcBlockAlarm NOTIFICATION-TYPE
			OBJECTS { hwPhysicalPortIfIndex, hwPhysicalPortName, hwAcBlockReason }
			STATUS current
			DESCRIPTION 
				"AC interface blocking alarm."
			::= { hwPortNotifications 253 }

		
		-- 1.3.6.1.4.1.2011.5.25.157.2.254
		hwAcBlockAlarmResume NOTIFICATION-TYPE
			OBJECTS { hwPhysicalPortIfIndex, hwPhysicalPortName, hwAcBlockReason }
			STATUS current
			DESCRIPTION 
				"AC interface blocking alarm clearing."
			::= { hwPortNotifications 254 }
     -- 1.3.6.1.4.1.2011.5.25.157.2.255
    hwPortLicenseActFail NOTIFICATION-TYPE
        OBJECTS {hwGtlItemName,
            hwPhysicalPortIfIndex,
            hwPhysicalPortName}
        STATUS current
        DESCRIPTION
            "This object indicates that the license for a physical interface fails to be activated."
        ::= { hwPortNotifications 255 }
    -- 1.3.6.1.4.1.2011.5.25.157.2.256
    hwPortLicenseActSuccess NOTIFICATION-TYPE
        OBJECTS {hwGtlItemName,
            hwPhysicalPortIfIndex,
            hwPhysicalPortName}
        STATUS current
        DESCRIPTION
            "This object indicates that the license for a physical interface is successfully activated."
        ::= { hwPortNotifications 256 }  
        
    -- 1.3.6.1.4.1.2011.5.25.157.2.257    
    hwCableSnrAbnormal NOTIFICATION-TYPE
		OBJECTS {
			hwPhysicalPortIfIndex,
			hwPhysicalPortName}
		STATUS current
		DESCRIPTION
			"The network cable is of poor quality."
		::= { hwPortNotifications 257 }  
		
    -- 1.3.6.1.4.1.2011.5.25.157.2.258    
    hwCableSnrNormal NOTIFICATION-TYPE
		OBJECTS {
			hwPhysicalPortIfIndex,
			hwPhysicalPortName}
		STATUS current
		DESCRIPTION
			"The network cable is of good quality."
		::= { hwPortNotifications 258 } 
		
    -- 1.3.6.1.4.1.2011.5.25.157.2.259    
    hwCableSnrDetectNotSupport NOTIFICATION-TYPE
		OBJECTS {
			hwPhysicalPortIfIndex,
			hwPhysicalPortName}
		STATUS current
		DESCRIPTION
			"The network cable quality cannot be detected."
		::= { hwPortNotifications 259 }

    -- 1.3.6.1.4.1.2011.5.25.157.2.260
    hwFlexEPhyNumberMismatch NOTIFICATION-TYPE
        OBJECTS {hwPhysicalPortIfIndex, hwPhysicalPortName, hwPhysicalPortLocalPhyNum, hwPhysicalPortRemotePhyNum}
        STATUS current
        DESCRIPTION
            "Indicates the alarm is detected."
        ::= { hwPortNotifications 260 }  
        
    -- 1.3.6.1.4.1.2011.5.25.157.2.261
    hwFlexEPhyNumberMismatchResume NOTIFICATION-TYPE
        OBJECTS {hwPhysicalPortIfIndex, hwPhysicalPortName, hwPhysicalPortLocalPhyNum, hwPhysicalPortRemotePhyNum}
        STATUS current
        DESCRIPTION
            "Indicates the alarm is cleared."
        ::= { hwPortNotifications 261 } 
        
    -- 1.3.6.1.4.1.2011.5.25.157.2.262
    hwFlexEPhyGroupMismatch NOTIFICATION-TYPE
        OBJECTS {hwPhysicalPortIfIndex, hwPhysicalPortName, hwPhysicalPortLocalGroupID, hwPhysicalPortRemteGroupID}
        STATUS current
        DESCRIPTION
            "Indicates the alarm is detected."
        ::= { hwPortNotifications 262 }  
        
    -- 1.3.6.1.4.1.2011.5.25.157.2.263
    hwFlexEPhyGroupMismatchResume NOTIFICATION-TYPE
        OBJECTS {hwPhysicalPortIfIndex, hwPhysicalPortName, hwPhysicalPortLocalGroupID, hwPhysicalPortRemteGroupID}
        STATUS current
        DESCRIPTION
            "Indicates the alarm is cleared."
        ::= { hwPortNotifications 263 } 
        
    -- 1.3.6.1.4.1.2011.5.25.157.2.264
    hwFlexEClientIDMismatch NOTIFICATION-TYPE
        OBJECTS {hwPhysicalPortIfIndex, hwPhysicalPortName}
        STATUS current
        DESCRIPTION
            "Indicates the alarm is detected."
        ::= { hwPortNotifications 264 }  
        
    -- 1.3.6.1.4.1.2011.5.25.157.2.265
    hwFlexEClientIDMismatchResume NOTIFICATION-TYPE
        OBJECTS {hwPhysicalPortIfIndex, hwPhysicalPortName}
        STATUS current
        DESCRIPTION
            "Indicates the alarm is cleared."
        ::= { hwPortNotifications 265 }      
        
    -- 1.3.6.1.4.1.2011.5.25.157.2.266
    hwFlexEBwReduceAlarm NOTIFICATION-TYPE
        OBJECTS {hwPhysicalPortIfIndex, hwPhysicalPortName, hwPhysicalPortBW}
        STATUS current
        DESCRIPTION
            "Indicates the alarm is detected."
        ::= { hwPortNotifications 266 }  
        
    -- 1.3.6.1.4.1.2011.5.25.157.2.267
    hwFlexEBwReduceAlarmResume NOTIFICATION-TYPE
        OBJECTS {hwPhysicalPortIfIndex, hwPhysicalPortName, hwPhysicalPortBW}
        STATUS current
        DESCRIPTION
            "Indicates the alarm is cleared."
        ::= { hwPortNotifications 267 } 

    -- 1.3.6.1.4.1.2011.5.25.157.2.268
    hwFlexEPhyFcsSdAlarm NOTIFICATION-TYPE
        OBJECTS {hwPhysicalPortIfIndex, hwPhysicalPortName }
        STATUS current
        DESCRIPTION
            "Indicates the alarm is detected."
        ::= { hwPortNotifications 268 }         

    -- 1.3.6.1.4.1.2011.5.25.157.2.269
    hwFlexEPhyFcsSdAlarmResume NOTIFICATION-TYPE
        OBJECTS {hwPhysicalPortIfIndex, hwPhysicalPortName}
        STATUS current
        DESCRIPTION
            "Indicates the alarm is cleared."
        ::= { hwPortNotifications 269 }     

    -- 1.3.6.1.4.1.2011.5.25.157.2.270
    hwFlexEPhyLocalFaultAlarm NOTIFICATION-TYPE
        OBJECTS {hwPhysicalPortIfIndex, hwPhysicalPortName }
        STATUS current
        DESCRIPTION
            "Indicates the alarm is detected."
        ::= { hwPortNotifications 270 }         

    -- 1.3.6.1.4.1.2011.5.25.157.2.271
    hwFlexEPhyLocalFaultAlarmResume NOTIFICATION-TYPE
        OBJECTS {hwPhysicalPortIfIndex, hwPhysicalPortName}
        STATUS current
        DESCRIPTION
            "Indicates the alarm is cleared."
        ::= { hwPortNotifications 271 }      

    -- 1.3.6.1.4.1.2011.5.25.157.2.272
    hwFlexEPhyRemoteFaultAlarm NOTIFICATION-TYPE
        OBJECTS {hwPhysicalPortIfIndex, hwPhysicalPortName }
        STATUS current
        DESCRIPTION
            "Indicates the alarm is detected."
        ::= { hwPortNotifications 272 }         

    -- 1.3.6.1.4.1.2011.5.25.157.2.273
    hwFlexEPhyRemoteFaultAlarmResume NOTIFICATION-TYPE
        OBJECTS {hwPhysicalPortIfIndex, hwPhysicalPortName}
        STATUS current
        DESCRIPTION
            "Indicates the alarm is cleared."
        ::= { hwPortNotifications 273 }         
        
    -- 1.3.6.1.4.1.2011.5.25.157.2.274
    hwFlexEBwMismatch NOTIFICATION-TYPE
        OBJECTS {hwPhysicalPortIfIndex, hwPhysicalPortName }
        STATUS current
        DESCRIPTION
            "Indicates the alarm is detected."
        ::= { hwPortNotifications 274}         

    -- 1.3.6.1.4.1.2011.5.25.157.2.275
    hwFlexEBwMismatchResume NOTIFICATION-TYPE
        OBJECTS {hwPhysicalPortIfIndex, hwPhysicalPortName}
        STATUS current
        DESCRIPTION
            "Indicates the alarm is cleared."
        ::= { hwPortNotifications 275 }
        
    -- 1.3.6.1.4.1.2011.5.25.157.2.276
    hwFlexEPhyDelayOverAlarm NOTIFICATION-TYPE
        OBJECTS {hwPhysicalPortIfIndex, hwPhysicalPortList }
        STATUS current
        DESCRIPTION
            "Indicates the alarm is detected."
        ::= { hwPortNotifications 276}         

    -- 1.3.6.1.4.1.2011.5.25.157.2.277
    hwFlexEPhyDelayOverAlarmResume NOTIFICATION-TYPE
        OBJECTS {hwPhysicalPortIfIndex, hwPhysicalPortList}
        STATUS current
        DESCRIPTION
            "Indicates the alarm is cleared."
        ::= { hwPortNotifications 277 }    

    -- 1.3.6.1.4.1.2011.5.25.157.2.278
    hwFlexESubTimeSlotMismatch NOTIFICATION-TYPE
        OBJECTS {hwPhysicalPortIfIndex, hwPhysicalPortName }
        STATUS current
        DESCRIPTION
            "Indicates the alarm is detected."
        ::= { hwPortNotifications 278}         

    -- 1.3.6.1.4.1.2011.5.25.157.2.279
    hwFlexESubTimeSlotMismatchResume NOTIFICATION-TYPE
        OBJECTS {hwPhysicalPortIfIndex, hwPhysicalPortName}
        STATUS current
        DESCRIPTION
            "Indicates the alarm is cleared."
        ::= { hwPortNotifications 279 }   

    -- 1.3.6.1.4.1.2011.5.25.157.2.280
    hwVxlanTrunkHashNotSupport NOTIFICATION-TYPE
        OBJECTS {hwPhysicalPortThrIfIndex, hwPhysicalPortThrName}
        STATUS current
        DESCRIPTION
            "The Eth-Trunk can not function normally as an outbound interface for vxlan packets when IP address-based load balancing is configured."
        ::= { hwPortNotifications 280 }       

    -- 1.3.6.1.4.1.2011.5.25.157.2.281
    hwPvcNumAlarm NOTIFICATION-TYPE
           OBJECTS { hwAtmPWAlarmIfIndex, hwAtmPWPortName }
            STATUS current
            DESCRIPTION 
                "PVC number exceeded the upper threshold."
            ::= { hwPortNotifications 281 } 
               
    -- 1.3.6.1.4.1.2011.5.25.157.2.282
    hwPvcNumAlarmResume NOTIFICATION-TYPE
           OBJECTS { hwAtmPWAlarmIfIndex, hwAtmPWPortName }
            STATUS current
            DESCRIPTION 
                "PVC number alarm resumed."
            ::= { hwPortNotifications 282 } 	

    -- 1.3.6.1.4.1.2011.5.25.157.2.283
    hwEthoamClosePortAlarm NOTIFICATION-TYPE
           OBJECTS { hwPhysicalPortInChassis, hwPhysicalPortInSlot, hwPhysicalPortInCard, hwPhysicalPortInPort, hwPhysicalPortName, hwMepId, hwUniName}
            STATUS current
            DESCRIPTION 
                "The service interface is disabled by Ethernet OAM."
            ::= { hwPortNotifications 283 } 

    -- 1.3.6.1.4.1.2011.5.25.157.2.284
    hwPortTypeChangeTrap NOTIFICATION-TYPE
			OBJECTS {
				hwPhysicalPortIfIndex,
				hwPhysicalPortName,
				hwPhysicalPortMode}
			STATUS current
			DESCRIPTION 
				"The mode of combo port is changed."
			::= { hwPortNotifications 284 }	

    -- 1.3.6.1.4.1.2011.5.25.157.2.285
    hwComboSwitchFail NOTIFICATION-TYPE
			OBJECTS {
				hwPhysicalPortIfIndex,
				hwPhysicalPortName,
				hwPhysicalPortAlarmReason}
			STATUS current
			DESCRIPTION 
				"Combo switch fail alarm."
			::= { hwPortNotifications 285 }	

    -- 1.3.6.1.4.1.2011.5.25.157.2.286
    hwComboSwitchFailResume NOTIFICATION-TYPE
			OBJECTS {
				hwPhysicalPortIfIndex,
				hwPhysicalPortName,
				hwPhysicalPortAlarmReason}
			STATUS current
			DESCRIPTION 
				"Combo switch fail alarm resume."
			::= { hwPortNotifications 286 }

    -- 1.3.6.1.4.1.2011.5.25.157.2.287
    hwEthoamClosePortAlarmResume NOTIFICATION-TYPE
           OBJECTS { hwPhysicalPortInChassis, hwPhysicalPortInSlot, hwPhysicalPortInCard, hwPhysicalPortInPort, hwPhysicalPortName, hwMepId, hwUniName}
            STATUS current
            DESCRIPTION 
                "The service interface is undo disable by Ethernet OAM."
            ::= { hwPortNotifications 287 } 


    hwPortTotalStatistics OBJECT IDENTIFIER ::= { hwPortMIBObjects 25 }
    
		-- 1.3.6.1.4.1.2011.5.25.157.1.25.1
		hwPortTotalStatTable OBJECT-TYPE
			SYNTAX SEQUENCE OF HwPortTotalStatEntry
			MAX-ACCESS not-accessible
			STATUS current
			DESCRIPTION
				"This table lists the port total statistics."
			::= { hwPortTotalStatistics 1 }
		
		-- 1.3.6.1.4.1.2011.5.25.157.1.25.1.1
		hwPortTotalStatEntry OBJECT-TYPE
			SYNTAX HwPortTotalStatEntry
			MAX-ACCESS not-accessible
			STATUS current
			DESCRIPTION
				"Indicates the port total statistics."
			INDEX { hwPortTotalStatIfIndex }
			::= { hwPortTotalStatTable 1 }
		
		HwPortTotalStatEntry ::=
			SEQUENCE { 
				hwPortTotalStatIfIndex
					InterfaceIndex,
				hwPortTotalStatIfName
					OCTET STRING,
				hwPortTotalStatInPkts
					Counter64,
				hwPortTotalStatInOctets
					Counter64,
				hwPortTotalStatInErrors
					Counter64,
				hwPortTotalStatOutPkts
					Counter64,
				hwPortTotalStatOutOctets
					Counter64,
				hwPortTotalStatOutErrors
					Counter64
			 }

		-- 1.3.6.1.4.1.2011.5.25.157.1.25.1.1.1
		hwPortTotalStatIfIndex OBJECT-TYPE
			SYNTAX InterfaceIndex
			MAX-ACCESS read-only
			STATUS current
			DESCRIPTION
				"The index of this interface."
			::= { hwPortTotalStatEntry 1 }
		
		-- 1.3.6.1.4.1.2011.5.25.157.1.25.1.1.2
		hwPortTotalStatIfName OBJECT-TYPE
			SYNTAX OCTET STRING (SIZE (0..64))
			MAX-ACCESS read-only
			STATUS current
			DESCRIPTION
				"The name of this interface."
			::= { hwPortTotalStatEntry 2 }
		
		-- 1.3.6.1.4.1.2011.5.25.157.1.25.1.1.3
		hwPortTotalStatInPkts OBJECT-TYPE
			SYNTAX Counter64
			MAX-ACCESS read-only
			STATUS current
			DESCRIPTION
				"Received total Pkts stat of this interface."
			::= { hwPortTotalStatEntry 3 }
		
		-- 1.3.6.1.4.1.2011.5.25.157.1.25.1.1.4
		hwPortTotalStatInOctets OBJECT-TYPE
			SYNTAX Counter64
			MAX-ACCESS read-only
			STATUS current
			DESCRIPTION
				"Received total Octets stat of this interface."
			::= { hwPortTotalStatEntry 4 } 
			
		-- 1.3.6.1.4.1.2011.5.25.157.1.25.1.1.5
		hwPortTotalStatInErrors OBJECT-TYPE
			SYNTAX Counter64
			MAX-ACCESS read-only
			STATUS current
			DESCRIPTION
				"Received total error Pkts stat of this interface."
			::= { hwPortTotalStatEntry 5 }  
		
		-- 1.3.6.1.4.1.2011.5.25.157.1.25.1.1.6
		hwPortTotalStatOutPkts OBJECT-TYPE
			SYNTAX Counter64
			MAX-ACCESS read-only
			STATUS current
			DESCRIPTION
				"Send total Pkts stat of this interface."
			::= { hwPortTotalStatEntry 6 }
		
		-- 1.3.6.1.4.1.2011.5.25.157.1.25.1.1.7
		hwPortTotalStatOutOctets OBJECT-TYPE
			SYNTAX Counter64
			MAX-ACCESS read-only
			STATUS current
			DESCRIPTION
				"Send total Octets stat of this interface."
			::= { hwPortTotalStatEntry 7 }
   
   		-- 1.3.6.1.4.1.2011.5.25.157.1.25.1.1.8
		hwPortTotalStatOutErrors OBJECT-TYPE
			SYNTAX Counter64
			MAX-ACCESS read-only
			STATUS current
			DESCRIPTION
				"Send total error Pkts stat of this interface."
			::= { hwPortTotalStatEntry 8 }

		-- 1.3.6.1.4.1.2011.5.25.157.1.26
		hwSubIfNumExceededSpecTrapObject OBJECT IDENTIFIER ::= { hwPortMIBObjects 26 }

		
		-- 1.3.6.1.4.1.2011.5.25.157.1.26.1
		hwSubIfSpecNum OBJECT-TYPE
			SYNTAX Integer32
			MAX-ACCESS accessible-for-notify
			STATUS current
			DESCRIPTION
				"The number of sub interface spec."
			::= { hwSubIfNumExceededSpecTrapObject 1 }
			
		-- 1.3.6.1.4.1.2011.5.25.157.1.27
		hwPortSpeedTrapObjects OBJECT IDENTIFIER ::= { hwPortMIBObjects 27 }
		
		-- 1.3.6.1.4.1.2011.5.25.157.1.27.1
		hwPhysicalPortCurSpeed OBJECT-TYPE
			SYNTAX Integer32
			MAX-ACCESS accessible-for-notify
			STATUS current
			DESCRIPTION
				"The speed of port after change."
			::= { hwPortSpeedTrapObjects 1 }
		
		-- 1.3.6.1.4.1.2011.5.25.157.1.27.2
		hwPhysicalPortLastSpeed OBJECT-TYPE
			SYNTAX Integer32
			MAX-ACCESS accessible-for-notify
			STATUS current
			DESCRIPTION
				"The speed of port before change."
			::= { hwPortSpeedTrapObjects 2 }

    hwPortConformance OBJECT IDENTIFIER ::= { hwPortMIB 11 }

    hwPortCompliances OBJECT IDENTIFIER ::= { hwPortConformance 1 }

    hwPortCompliance MODULE-COMPLIANCE
        STATUS current
        DESCRIPTION
            "The compliance statement for systems supporting
                the HUAWEI-PORT-MIB."
        MODULE 
            MANDATORY-GROUPS {hwEthernetObjectGroup,hwPosObjectGroup,hwCposObjectGroup,hwBundleSerialObjectGroup,hwDs0ChannelBundleObjectGroup,hwDs1ObjectGroup,hwDs3ObjectGroup,hwPortNotificationsGroup,hwPortAlarmThresholdObjectGroup,hwPortAlarmDownEnableObjectGroup,hwLogicalPortObjectGroup,hwPortSpeedTrapObjectsGroup}

        ::= { hwPortCompliances 1 }


    hwPortGroups OBJECT IDENTIFIER ::= { hwPortConformance 2 }

    hwEthernetObjectGroup OBJECT-GROUP

        OBJECTS {
            hwEthernetLoopback,
            hwEthernetPortType,
            hwEthernetSpeedSet,
            hwEthernetDuplex,
            hwEthernetNegotiation,
            hwEthernetPortTypeOperate,
            hwEthernetClock,
            hwEthernetFlagJ0Mode,
            hwEthernetFlagJ0Value,
            hwEthernetFlagJ0Trace,
            hwEthernetFlagJ1Mode,
            hwEthernetFlagJ1Value,
            hwEthernetFlagJ1Trace,
            hwEthernetFlagC2Value,
            hwEthernetUpHoldTime,
            hwEthernetDownHoldTime,
            hwEthernetSubinterfaceStatisticEnable,
            hwEthernetJumboframeMaxLength,
            hwEthernetComboType,
            hwEthernetPortMode
        }
        STATUS current
        DESCRIPTION
            "The Port attribute group."
        ::= { hwPortGroups 1 }

    hwPosObjectGroup OBJECT-GROUP

        OBJECTS {
            hwPosLinkProtocol,
            hwPosFrameFormat,
            hwPosLoopback,
            hwPosScramble,
            hwPosClock,
            hwPosCrcVerifyCode,
            hwPosFlagJ0Mode,
            hwPosFlagJ0Value,
            hwPosFlagJ0Trace,
            hwPosFlagJ1Mode,
            hwPosFlagJ1Value,
            hwPosFlagJ1Trace,
            hwPosFlagC2Value
        }
        STATUS current
        DESCRIPTION
            "The Port attribute group."
        ::= { hwPortGroups 2 }

    hwCposObjectGroup OBJECT-GROUP

        OBJECTS {
            hwCposFrameFormat,
            hwCposMultiplex,
            hwCposClock,
            hwCposIfType,
            hwCposLoopback,
            hwCposFlagJ0Mode,
            hwCposFlagJ0Value,
            hwCposFlagJ0Trace,
            hwCposFlagJ1Mode,
            hwCposFlagJ1Value,
            hwCposFlagJ1Trace,
            hwCposFlagC2Value,
            hwCposB1SdAlarmThreshold,
            hwCposB1ExcAlarmThreshold,
            hwCposB2SdAlarmThreshold,
            hwCposB2ExcAlarmThreshold,
            hwCposB3SdAlarmThreshold,
            hwCposB3ExcAlarmThreshold,
            hwCposLpBipSdAlarmThreshold,
            hwCposLpBipExcAlarmThreshold,
            hwCposHighPathNumber,
            hwCposLowPathNumber,
            hwCposMappingMode
        }
        STATUS current
        DESCRIPTION
            "The Port attribute group."
        ::= { hwPortGroups 3 }

    hwDs0ChannelBundleObjectGroup OBJECT-GROUP

        OBJECTS {
            hwDs0ChannelBundleIfIndex,
            hwDs0ChannelBundleTimeSlots,
            hwDs0ChannelBundleSpeed,
            hwDs0ChannelBundleIsMasterPW,
            hwDs0ChannelBundleMasterPWStatus,
            hwDs0ChannelBundlePortName,
            hwDs0ChannelBundleRowStatus
        }
        STATUS current
        DESCRIPTION
            "The Port attribute group."
        ::= { hwPortGroups 4 }

    hwDs1ObjectGroup OBJECT-GROUP

        OBJECTS {
            hwDs1ChannelType,
            hwDs1IfType,
            hwDs1Channelized,
            hwDs1CodeType,
            hwDs1Clock,
            hwDs1FrameFormat,
            hwDs1Cable,
            hwDs1Loopback,
            hwDs1ClockRecoveryDomain,
            hwDs1PWClockDomain,
            hwDs1WorkMode,
            hwDs1RowStatus
        }
        STATUS current
        DESCRIPTION
            "The Port attribute group."
        ::= { hwPortGroups 5 }

    hwDs3ObjectGroup OBJECT-GROUP

        OBJECTS {
            hwDs3ChannelType,
            hwDs3IfType,
            hwDs3Channelized,
            hwDs3Clock,
            hwDs3FrameFormat,
            hwDs3Scramble,
            hwDs3Cable,
            hwDs3NationalBit,
            hwDs3Loopback,
            hwDs3CreateSerial,
            hwDs3RowStatus
        }
        STATUS current
        DESCRIPTION
            "The Port attribute group."
        ::= { hwPortGroups 6 }

    hwBundleSerialObjectGroup OBJECT-GROUP

        OBJECTS {
            hwBundleSerialLinkProtocol,
            hwBundleSerialTimerHold,
            hwBundleSerialCrcVerifyCode,
            hwBundleSerialLoopback
        }
        STATUS current
        DESCRIPTION
            "The Port attribute group."
        ::= { hwPortGroups 7 }

    hwPortNotificationsGroup NOTIFICATION-GROUP
        NOTIFICATIONS {
            hwPortACRMasterPWChange,
            hwHpJ1TiuAlarm,
            hwHpJ1TiuAlarmResume,
            hwCesPwOppositeAcFault,
            hwCesPwOppositeAcFaultResume,
            hwCesLosPktExcAlarm,
            hwCesLosPktExcAlarmResume,
            hwCesMisorderPktExcAlarm,
            hwCesMisorderPktExcAlarmResume,
            hwCesStrayPktExcAlarm,
            hwCesStrayPktExcAlarmResume,
            hwCesMalPktExcAlarm,
            hwCesMalPktExcAlarmResume,
            hwCesJtrUdrExcAlarm,
            hwCesJtrUdrExcAlarmResume,
            hwCesJtrOvrExcAlarm,
            hwCesJtrOvrExcAlarmResume,
            hwLaserShutAlarm,
            hwLaserShutAlarmResume,
            hwLaserAutoShutAlarm,
            hwLaserAutoShutAlarmResume,
            hwLoopbackAlarm,
            hwLoopbackAlarmResume,
            hwChannelLoopbackAlarm,
            hwChannelLoopbackAlarmResume,
            hwCesPwOppositeRaiResume,
            hwCesPwOppositeRai,
            hwB1TcaAlarm,
            hwB1TcaAlarmResume,
            hwB2TcaAlarm,
            hwB2TcaAlarmResume,
            hwOofAlarm,
            hwOofAlarmResume,
            hwLosAlarm,
            hwLosAlarmResume,
            hwJ0TimAlarm,
            hwJ0TimAlarmResume,
            hwLrdiAlarm,
            hwLrdiAlarmResume,
            hwSfbereAlarm,
            hwSfbereAlarmResume,
            hwAuLopAlarm,
            hwAuLopAlarmResume,
            hwLaisAlarm,
            hwLaisAlarmResume,
            hwSdbereAlarm,
            hwSdbereAlarmResume,
            hwPtimAlarm,
            hwPtimAlarmResume,
            hwPuneqAlarm,
            hwPuneqAlarmResume,
            hwPrdiAlarm,
            hwPrdiAlarmResume,
            hwB3TcaAlarm,
            hwB3TcaAlarmResume,
            hwPplmAlarm,
            hwPplmAlarmResume,
            hwPaisAlarm,
            hwPaisAlarmResume,
            hwAuAisAlarm,
            hwAuAisAlarmResume,
            hwVlopAlarm,
            hwVlopAlarmResume,
            hwLomAlarm,
            hwLomAlarmResume,
            hwLpTimVc12Alarm,
            hwLpTimVc12AlarmResume,
            hwLofAlarm,
            hwLofAlarmResume,
            hwCesPwRemoteLosPktAlarm,
            hwCesPwRemoteLosPktAlarmResume,
            hwLpUneqVc12Alarm,
            hwLpUneqVc12AlarmResume,
            hwVrdiAlarm,
            hwVrdiAlarmResume,
            hwBip2TcaAlarm,
            hwBip2TcaAlarmResume,
            hwLpSlmVc12Alarm,
            hwLpSlmVc12AlarmResume,
            hwTuAisVc12Alarm,
            hwTuAisVc12AlarmResume,
            hwE1EsTcaAlarm,
            hwE1EsTcaAlarmResume,
            hwE1LmfaAlarm,
            hwE1LmfaAlarmResume,
            hwE1UpE1AisAlarm,
            hwE1UpE1AisAlarmResume,
            hwE1AlmE1RaiAlarm,
            hwE1AlmE1RaiAlarmResume,
            hwRroolAlarm,
            hwRroolAlarmResume,
            hwVrfiAlarm,
            hwVrfiAlarmResume,
            hwV5VcaisAlarm,
            hwV5VcaisAlarmResume,
            hwCposE1AlmE1RaiAlarm,
            hwCposE1AlmE1RaiAlarmResume,
            hwCposE1LfaAlarm,
            hwCposE1LfaAlarmResume,
            hwCposE1UpE1AisAlarm,
            hwCposE1UpE1AisAlarmResume,
            hwCposE1DownE1AisAlarm,
            hwCposE1DownE1AisAlarmResume,
            hwE1DownE1AisAlarm,
            hwE1DownE1AisAlarmResume,
            hwCposE1LmfaAlarm,
            hwCposE1LmfaAlarmResume,
            hwOcdAlarm,
            hwOcdAlarmResume,
            hwLcdAlarm,
            hwLcdAlarmResume,
            hwUhcsAlarm,
            hwUhcsAlarmResume,
            hwChcsAlarm,
            hwChcsAlarmResume,
            hwCesLopsAlarm,
            hwCesLopsAlarmResume,
            hwAtmPwLosPktExcAlarm,
            hwAtmPwLosPktExcAlarmResume,
            hwAtmPwMisorderPktExcAlarm,
            hwAtmPwMisorderPktExcAlarmResume,
            hwAtmPwUnknownCellExcAlarm,
            hwAtmPwUnknownCellExcAlarmResume,
            hwPortAlarmInverseAutoRecover,
            hwB1ExcAlarm,
            hwB1ExcAlarmResume,
            hwBip2ExcAlarm,
            hwBip2ExcAlarmResume,
            hwB3ExcAlarm,
            hwB3ExcAlarmResume,
            hwLoopBackAutoClearNotice,
            hwChannelLoopBackAutoClearNotice,
            hwHpJ1TiuAlarm,
            hwHpJ1TiuAlarmResume,
            hwPortAlarmInverseAutoRecover,
            hwB3ExcAlarm,
            hwB3ExcAlarmResume,
            hwBip2ExcAlarm,
            hwBip2ExcAlarmResume,
            hwLicenseLimitAlarm,
            hwLicenseLimitAlarmResume,
            hwRemoteFaultAlarm,
            hwRemoteFaultAlarmResume,
            hwOpticalModuleIsNotAuthorizedResume,
            hwLocalFaultAlarm,
            hwLocalFaultAlarmResume,
            hwOpticalModuleIsNotAuthorized,
            hwCopperPolarityError,
            hwCopperPolarityErrorResume,
            hwLotuaisAlarm,
            hwLotuaisAlarmResume,
            hwLotulomAlarm,
            hwLotulomAlarmResume,
            hwLotusdberAlarm,
            hwLotusdberAlarmResume,
            hwLotusfberAlarm,
            hwLotusfberAlarmResume,
            hwLoduaisAlarm,
            hwLoduaisAlarmResume,
            hwLodulckAlarm,
            hwLodulckAlarmResume,
            hwLoduociAlarm,
            hwLoduociAlarmResume,
            hwLpmbdiAlarm,
            hwLpmbdiAlarmResume,
            hwLpmtimAlarm,
            hwLpmtimAlarmResume,
            hwLsmbdiAlarm,
            hwLsmbdiAlarmResume,
            hwLsmiaeAlarm,
            hwLsmiaeAlarmResume,
            hwLsmtimAlarm,
            hwLsmtimAlarmResume,
            hwNegotiationFailedAlarm,
            hwNegotiationFailedAlarmResume,
            hwEthHalfDuplex ,
            hwEthFullDuplex,
            hwE3UpE3AisAlarm,
            hwE3UpE3AisAlarmResume,
            hwE3AlmE3RaiAlarm,
            hwE3AlmE3RaiAlarmResume,
            hwInputRateChangeOverThresholdNotice,
            hwOutputRateChangeOverThresholdNotice,
            hwPortPhysicalRateDegradeAlarm,
            hwPortPhysicalRateDegradeAlarmResume,
            hwPortModeChangeTrap,
             hwRdiAlarm,
            hwRdiAlarmResume,
            hwAisAlarm,
            hwAisAlarmResume,
            hwCollisionAlarm,
            hwCollisionAlarmResume,
            hwPortSpeedChangeTrap,
      hwPortGroupTransModeDiff,
           hwPortGroupTransModeDiffResume,
		   hwPicLcdAlarm,
		    hwPicLcdAlarmResume,  
			hwBoardNotSupportAssignTrunk,
			hwPortProtectGroupUnavailable,  
			hwPortProtectGroupAvailable, 
			hwPortProtectGroupDelete,
			hwPortLicenseActFail,
			hwPortLicenseActSuccess,
			hwCableSnrAbnormal,
			hwCableSnrNormal,
			hwCableSnrDetectNotSupport,
            hwFlexEPhyNumberMismatch,
            hwFlexEPhyNumberMismatchResume,
            hwFlexEPhyGroupMismatch,
            hwFlexEPhyGroupMismatchResume,
            hwFlexEClientIDMismatch,
            hwFlexEClientIDMismatchResume,
            hwFlexEBwReduceAlarm,
            hwFlexEBwReduceAlarmResume,
            hwFlexEPhyFcsSdAlarm,
            hwFlexEPhyFcsSdAlarmResume,
            hwFlexEPhyLocalFaultAlarm,
            hwFlexEPhyLocalFaultAlarmResume,
            hwFlexEPhyRemoteFaultAlarm,
            hwFlexEPhyRemoteFaultAlarmResume,
            hwFlexEBwMismatch,
            hwFlexEBwMismatchResume,
            hwFlexEPhyDelayOverAlarm,
            hwFlexEPhyDelayOverAlarmResume,
            hwFlexESubTimeSlotMismatch,
            hwFlexESubTimeSlotMismatchResume,
            hwVxlanTrunkHashNotSupport,            
            hwPvcNumAlarm,
            hwPvcNumAlarmResume,
            hwEthoamClosePortAlarm,
            hwPortTypeChangeTrap,
            hwComboSwitchFail,
            hwComboSwitchFailResume,
            hwEthoamClosePortAlarmResume
         }
        STATUS current
        DESCRIPTION
            "This is the group of port notifiction."
        ::= { hwPortGroups 8 }

    hwDslGroupObjectGroup OBJECT-GROUP

        OBJECTS {
            hwDslGroupIfIndex,
            hwDslGroupWorkMode,
            hwDslGroupBisState,
            hwDslGroupEncapeMode,
            hwDslGroupEnable,
            hwDslGroupRowStatus,
            hwDslGroupIfIndexOfBound,
            hwVirtualEthernetIfIndex,
            hwBoundVeRowStatus,
            hwDslGroupVci,
            hwDslGroupVpi,
            hwDslGroupPvcId
        }
        STATUS current
        DESCRIPTION
            "The dsl group attribute group."
        ::= { hwPortGroups 9 }

    hwDslGroupImaObjectGroup OBJECT-GROUP

        OBJECTS {
            hwDslGroupImaVersion,
            hwDslGroupImaFrameLen,
            hwDslGroupImaReset,
            hwDslGroupImaRxMinLinkNum,
            hwDslGroupImaNeState,
            hwDslGroupImaRxActLinkNum,
            hwDslGroupImaRxCellRate,
            hwDslGroupImaTxActLinkNum,
            hwDslGroupImaTxCellRate,
            hwDslGroupImaFeState,
            hwDslGroupImaIfIndex,
            hwDslGroupImaTxMinLinkNum,
            hwDslGroupImaIfName
        }
        STATUS current
        DESCRIPTION
            "The dsl group ima attribute group."
        ::= { hwPortGroups 10 }

    hwDslLinkObjectGroup OBJECT-GROUP

        OBJECTS {
            hwBoundDslGroupIfIndex,
            hwDslLinkIfIndex,
            hwDslLinkBoundRowStatus,
            hwDslLinkIfName,
            hwBoundDslGroupIfName
        }
        STATUS current
        DESCRIPTION
            "The dsl link attribute group."
        ::= { hwPortGroups 11 }

    hwDslImaTrapGroup NOTIFICATION-GROUP
        NOTIFICATIONS {
            hwDslImaGroupLEDown,
            hwDslImaGroupLEUp,
            hwDslImaGroupREDown,
            hwDslImaGroupREUp,
            hwDslImaLinkLif,
            hwDslImaLinkLifResume,
            hwDslImaLinkLods,
            hwDslImaLinkLodsResume,
            hwDslImaLinkRfi,
            hwDslImaLinkRfiResume,
            hwDslImaLinkReTxUnusable,
            hwDslImaLinkReTxUsable,
            hwDslImaLinkReRxUnusable,
            hwDslImaLinkReRxUsable
        }
        STATUS current
        DESCRIPTION
            "The dsl Ima Trap group."
        ::= { hwPortGroups 20 }

    hwDslLinkTrapGroup NOTIFICATION-GROUP
        NOTIFICATIONS {
            hwDslLinkFrameLost,
            hwDslLinkFrameResume,
            hwDslLinkSignalLost,
            hwDslLinkSignalResume
        }
        STATUS current
        DESCRIPTION
            "The dsl Link Trap group."
        ::= { hwPortGroups 21 }

    hwPortAlarmThresholdObjectGroup OBJECT-GROUP

        OBJECTS {
            hwPhysicalPortCrcErrorStatistics,
            hwPhysicalPortCrcErrorHighThreshold,
            hwPhysicalPortCrcErrorLowThreshold,
            hwPhysicalPortCrcErrorInterval,
            hwPhysicalPortSymbolErrorStatistics,
            hwPhysicalPortSymbolErrorHighThreshold,
            hwPhysicalPortSymbolErrorLowThreshold,
            hwPhysicalPortSymbolErrorInterval,
            hwPhysicalPortInputErrorStatistics,
            hwPhysicalPortInputErrorHighThreshold,
            hwPhysicalPortInputErrorLowThreshold,
            hwPhysicalPortInputErrorInterval,
            hwPhysicalPortOutputErrorStatistics,
            hwPhysicalPortOutputErrorHighThreshold,
            hwPhysicalPortOutputErrorLowThreshold,
            hwPhysicalPortOutputErrorInterval,
            hwPhysicalPortSdhErrorStatistics,
            hwPhysicalPortSdhErrorHighThreshold,
            hwPhysicalPortSdhErrorLowThreshold,
            hwPhysicalPortSdhErrorInterval,
            hwPhysicalPortBIP8SDErrorThreshold,
	    hwPhysicalPortCrcSdAlarmTriggerLsp,
	    hwPhysicalPortCrcExcAlarmTriggerLsp
        }
        STATUS current
        DESCRIPTION
            "The port alarm threshold group."
        ::= { hwPortGroups 22 }

    hwPortAlarmDownEnableObjectGroup OBJECT-GROUP

        OBJECTS {
            hwPhysicalPortCrcEnabledDown,
            hwPhysicalPortSymbolEnabledDown,
            hwPhysicalPortInputEnabledDown,
            hwPhysicalPortOutputEnabledDown,
            hwPhysicalPortSdhEnabledDown,
            hwPhysicalPortBip8SdEnabledDown
        }
        STATUS current
        DESCRIPTION
            "The port alarm down enable group."
        ::= { hwPortGroups 23 }

    hwLogicalPortObjectGroup OBJECT-GROUP

        OBJECTS {
            hwLogicalPortIfIndex,
            hwLogicalPortStatisticEnable
        }
        STATUS current
        DESCRIPTION
            "The Port attribute group."
        ::= { hwPortGroups 24 }

    hwPortAlarmTrapGroup NOTIFICATION-GROUP
        NOTIFICATIONS {
            hwPhysicalPortCrcError,
            hwPhysicalPortCrcErrorResume,
            hwPhysicalPortSymbolError,
            hwPhysicalPortSymbolErrorResume,
            hwPhysicalPortSdhError,
            hwPhysicalPortSdhErrorResume,
            hwPhysicalPortBip8SdError,
            hwPhysicalPortBip8SdErrorResume,
            hwPhysicalPortCrcPacketErrorRatio,
            hwPhysicalPortCrcPacketErrorRatioResume,
            hwPhysicalPortCrcSd, 
            hwPhysicalPortCrcSdResume, 
            hwPhysicalPortCrcExc, 
            hwPhysicalPortCrcExcResume, 
            hwPhysicalPortCrcPerWarning,
            hwPhysicalPortCrcPerWarningResume,
            hwPortCrcRateExceed,
            hwPortErrorRateExceed,
			hwPhysicalPortInBroadcastRapidChange,
            hwInputErrorAlarm,
            hwInputErrorAlarmResume,
            hwOutputErrorAlarm,
            hwOutputErrorAlarmResume,
            hwLicenseLimitAlarm,
            hwLicenseLimitAlarmResume,
            hwPhysicalPortAutoDetectFail,
            hwPhysicalPortAutoDetectSuccess,
            hwNotSameBoardInTrunk,
            hwInputBroadcastSurgeOccur,
            hwInputBroadcastSurgeResume,
            hwOutputBroadcastSurgeOccur,
            hwOutputBroadcastSurgeResume,
            hwLinkHeartbeatDropAlarm,
            hwLinkHeartbeatDropAlarmResume,
	    hwLinkHeartbeatChangeAlarm,
	    hwLinkHeartbeatChangeAlarmResume
	
        }
        STATUS current
        DESCRIPTION
            "The port alarm trap group."
        ::= { hwPortGroups 25 }

    hwPortPhysicalObjectGroup OBJECT-GROUP

        OBJECTS {
            hwPortPhysicalHpIndex,
            hwPortPhysicalLpIndex,
            hwLoopBackAutoClearEnable,
            hwPortAlarmInverseEnable,
            hwLoopBackAutoClearPeriod
        }
        STATUS current
        DESCRIPTION
            "The port physical object group."
        ::= { hwPortGroups 26 }

    hwPortProtectObjectGroup OBJECT-GROUP

        OBJECTS {
            hwPortProtectGroupId,
            hwPortProtectMasterIfIndex,
            hwPortProtectMasterStatus,
            hwPortProtectSlaveIfIndex,
            hwPortProtectSlaveStatus,
            hwPortProtectRowStatus
        }
        STATUS current
        DESCRIPTION
            "A collection of objects providing port protect group status information."
        ::= { hwPortGroups 27 } 
        
     hwPortDescriptinonObjectGroup OBJECT-GROUP

        OBJECTS {
            hwPortDescriptionIfIndex,
            hwPortDescriptionIfPortDescription
        }
        STATUS current
        DESCRIPTION
            "The port description object group"
        ::= { hwPortGroups 28 }


    -- 1.3.6.1.4.1.2011.5.25.157.11.2.29
    hwOtnAlarmNotificationsGroup NOTIFICATION-GROUP
        NOTIFICATIONS { hwOtuLomAlarm, hwOtuLomAlarmResume, hwOtuAisAlarm, hwOtuAisAlarmResume, 
                hwOtuSdAlarm, hwOtuSdAlarmResume, hwOtuSfAlarm, hwOtuSfAlarmResume, hwSmBdiAlarm, 
                hwSmBdiAlarmResume, hwSmIaeAlarm, hwSmIaeAlarmResume, hwSmTimAlarm, hwSmTimAlarmResume, 
                hwOduAisAlarm, hwOduAisAlarmResume, hwOduLokAlarm, hwOduLokAlarmResume, hwOduOciAlarm, 
                hwOduOciAlarmResume, hwPmBdiAlarm, hwPmBdiAlarmResume, hwPmTimAlarm, hwPmTimAlarmResume,
                hwPrefecTcaAlarm,hwPrefecTcaAlarmResume
                 }
        STATUS current
        DESCRIPTION 
                "This is the group of OTN port notifications."
        ::= { hwPortGroups 29 }
		
		-- 1.3.6.1.4.1.2011.5.25.157.11.2.30
		hwLinkHeartbeatObjectGroup OBJECT-GROUP
			OBJECTS { hwLinkHeartbeatIfindex, hwLinkHeartbeatIfName, hwLinkHeartbeatTxInterface, hwLinkHeartbeatRxInterface }
			STATUS current
			DESCRIPTION 
				"The link-heartbeat object group."
			::= { hwPortGroups 30 }

		hwPortTotalStatObjectGroup OBJECT-GROUP
			OBJECTS { hwPortTotalStatIfIndex,hwPortTotalStatIfName,hwPortTotalStatInPkts,hwPortTotalStatInOctets,hwPortTotalStatInErrors,hwPortTotalStatOutPkts,hwPortTotalStatOutOctets,hwPortTotalStatOutErrors }
			STATUS current
			DESCRIPTION 
				"The port total stat object group."
			::= { hwPortGroups 31 }

     hwPortSpeedTrapObjectsGroup OBJECT-GROUP

        OBJECTS {
            hwPhysicalPortCurSpeed,
            hwPhysicalPortLastSpeed
        }
        STATUS current
        DESCRIPTION
            "The port speed change trap object group"
        ::= { hwPortGroups 32 }
END
--
-- HUAWEI-PORT-MIB
