UPS-MIB DEFINITIONS ::= BEGIN

   IMPORTS
       MODULE-IDENTITY, OBJECT-TYPE, NOTIFICATION-TYPE,
       OBJECT-IDENTITY, Counter32, Gauge32, Integer32
           FROM SNMPv2-SMI
       DisplayString, TimeStamp, TimeInterval, TestAndIncr,
         AutonomousType
           FROM SNMPv2-TC
       MODULE-COMPLIANCE, OBJECT-GROUP
           FROM SNMPv2-CONF;

org            OBJECT IDENTIFIER ::= { iso 3 }  --  "iso" = 1
dod            OBJECT IDENTIFIER ::= { org 6 }
internet       OBJECT IDENTIFIER ::= { dod 1 }
mgmt           OBJECT IDENTIFIER ::= { internet 2 }
mib-2          OBJECT IDENTIFIER ::= { mgmt 1 }

   upsMIB MODULE-IDENTITY
       LAST-UPDATED "9402230000Z"
       ORGANIZATION "IETF UPS MIB Working Group"
       CONTACT-INFO
              "        Jeffrey D. Case

                Postal: SNMP Research, Incorporated
                        3001 Kimberlin Heights Road
                        Knoxville, TN  37920
                        US

                   Tel: +1 615 573 1434
                   Fax: +1 615 573 9197

                E-mail: case@snmp.com"
       DESCRIPTION
               "The MIB module to describe Uninterruptible Power
               Supplies. This version is extended for DIOAD."
       ::= { mib-2 33 }

   PositiveInteger ::= TEXTUAL-CONVENTION
       DISPLAY-HINT "d"
       STATUS       current
       DESCRIPTION
               "This data type is a non-zero and non-negative value."
       SYNTAX       INTEGER (1..2147483647)

   NonNegativeInteger ::= TEXTUAL-CONVENTION
       DISPLAY-HINT "d"
       STATUS       current
       DESCRIPTION
               "This data type is a non-negative value."
       SYNTAX       INTEGER (0..2147483647)

   upsObjects            OBJECT IDENTIFIER ::= { upsMIB 1 }

   --
   -- The Device Identification group.
   --      All objects in this group except for upsIdentName and
   --      upsIdentAttachedDevices are set at device initialization
   --      and remain static.
   --

   upsIdent              OBJECT IDENTIFIER ::= { upsObjects 1 }

   upsIdentManufacturer OBJECT-TYPE
       SYNTAX     DisplayString (SIZE (0..31))
       MAX-ACCESS read-only
       STATUS     current
       DESCRIPTION
               "The name of the UPS manufacturer."
       ::= { upsIdent 1 }

   upsIdentModel OBJECT-TYPE
       SYNTAX     DisplayString (SIZE (0..63))
       MAX-ACCESS read-only
       STATUS     current
       DESCRIPTION
               "The UPS Model designation."
       ::= { upsIdent 2 }

   upsIdentUPSSoftwareVersion OBJECT-TYPE
       SYNTAX     DisplayString (SIZE (0..63))
       MAX-ACCESS read-only
       STATUS     current
       DESCRIPTION
               "The UPS firmware/software version(s).  This variable
               may or may not have the same value as
               upsIdentAgentSoftwareVersion in some implementations."
       ::= { upsIdent 3 }

   upsIdentAgentSoftwareVersion OBJECT-TYPE
       SYNTAX     DisplayString (SIZE (0..63))
       MAX-ACCESS read-only
       STATUS     current
       DESCRIPTION
               "The UPS agent software version.  This variable may or
               may not have the same value as
               upsIdentUPSSoftwareVersion in some implementations."
       ::= { upsIdent 4 }

   upsIdentName OBJECT-TYPE
       SYNTAX     DisplayString (SIZE(0..63))
       MAX-ACCESS read-write
       STATUS     current
       DESCRIPTION
               "A string identifying the UPS.  This object should be
               set by the administrator."
       ::= { upsIdent 5 }

   upsIdentAttachedDevices OBJECT-TYPE
       SYNTAX     DisplayString (SIZE(0..63))
       MAX-ACCESS read-write
       STATUS     current
       DESCRIPTION
               "A string identifying the devices attached to the
               output(s) of the UPS.  This object should be set by
               the administrator."
       ::= { upsIdent 6 }


   --
   -- Battery Group
   --

   upsBattery            OBJECT IDENTIFIER ::= { upsObjects 2 }

   upsBatteryStatus OBJECT-TYPE
       SYNTAX     INTEGER {
           unknown(1),
           batteryNormal(2),
           batteryLow(3),
           batteryDepleted(4)
       }
       MAX-ACCESS read-only
       STATUS     current
       DESCRIPTION
               "The indication of the capacity remaining in the UPS
               system's batteries.   A value of batteryNormal
               indicates that the remaining run-time is greater than
               upsConfigLowBattTime.  A value of batteryLow indicates
               that the remaining battery run-time is less than or
               equal to upsConfigLowBattTime.  A value of
               batteryDepleted indicates that the UPS will be unable
               to sustain the present load when and if the utility
               power is lost (including the possibility that the
               utility power is currently absent and the UPS is
               unable to sustain the output)."
       ::= { upsBattery 1 }

   upsSecondsOnBattery OBJECT-TYPE
       SYNTAX     NonNegativeInteger
       UNITS      "seconds"
       MAX-ACCESS read-only
       STATUS     current
       DESCRIPTION
               "If the unit is on battery power, the elapsed time
               since the UPS last switched to battery power, or the
               time since the network management subsystem was last
               restarted, whichever is less.  Zero shall be returned
               if the unit is not on battery power."
       ::= { upsBattery 2 }

   upsEstimatedMinutesRemaining OBJECT-TYPE
       SYNTAX     PositiveInteger
       UNITS      "minutes"
       MAX-ACCESS read-only
       STATUS     current
       DESCRIPTION
               "An estimate of the time to battery charge depletion
               under the present load conditions if the utility power
               is off and remains off, or if it were to be lost and
               remain off."
       ::= { upsBattery 3 }

   upsEstimatedChargeRemaining OBJECT-TYPE
       SYNTAX     INTEGER (0..100)
       UNITS      "percent"
       MAX-ACCESS read-only
       STATUS     current
       DESCRIPTION
               "An estimate of the battery charge remaining expressed
               as a percent of full charge."
       ::= { upsBattery 4 }

   upsBatteryVoltage OBJECT-TYPE
       SYNTAX     NonNegativeInteger
       UNITS      "0.1 Volt DC"
       MAX-ACCESS read-only
       STATUS     current
       DESCRIPTION
               "The magnitude of the present battery voltage."
       ::= { upsBattery 5 }

   upsBatteryCurrent OBJECT-TYPE
       SYNTAX     Integer32
       UNITS      "0.1 Amp DC"
       MAX-ACCESS read-only
       STATUS     current
       DESCRIPTION
               "The present battery current."
       ::= { upsBattery 6 }

   upsBatteryTemperature OBJECT-TYPE
       SYNTAX     Integer32
       UNITS      "degrees Centigrade"
       MAX-ACCESS read-only
       STATUS     current
       DESCRIPTION
               "The ambient temperature at or near the UPS Battery
               casing."
       ::= { upsBattery 7 }


   --
   -- Input Group
   --

   upsInput              OBJECT IDENTIFIER ::= { upsObjects 3 }

   upsInputLineBads OBJECT-TYPE
       SYNTAX     Counter32
       MAX-ACCESS read-only
       STATUS     current
       DESCRIPTION
               "A count of the number of times the input entered an
               out-of-tolerance condition as defined by the
               manufacturer.  This count is incremented by one each
               time the input transitions from zero out-of-tolerance
               lines to one or more input lines out-of-tolerance."
       ::= { upsInput 1 }

   upsInputNumLines OBJECT-TYPE
       SYNTAX     NonNegativeInteger
       MAX-ACCESS read-only
       STATUS     current
       DESCRIPTION
               "The number of input lines utilized in this device.
               This variable indicates the number of rows in the
               input table."
       ::= { upsInput 2 }

   upsInputTable OBJECT-TYPE
       SYNTAX     SEQUENCE OF UpsInputEntry
       MAX-ACCESS not-accessible
       STATUS     current
       DESCRIPTION
               "A list of input table entries.  The number of entries
               is given by the value of upsInputNumLines."
       ::= { upsInput 3 }

   upsInputEntry OBJECT-TYPE
       SYNTAX     UpsInputEntry
       MAX-ACCESS not-accessible
       STATUS     current
       DESCRIPTION
               "An entry containing information applicable to a
               particular input line."
       INDEX { upsInputLineIndex }
       ::= { upsInputTable 1 }

   UpsInputEntry ::= SEQUENCE {
       upsInputLineIndex   PositiveInteger,
       upsInputFrequency   NonNegativeInteger,
       upsInputVoltage     NonNegativeInteger,
       upsInputCurrent     NonNegativeInteger,
       upsInputTruePower   NonNegativeInteger
   }

   upsInputLineIndex OBJECT-TYPE
       SYNTAX     PositiveInteger
       MAX-ACCESS not-accessible
       STATUS     current
       DESCRIPTION
               "The input line identifier."
       ::= { upsInputEntry 1 }

   upsInputFrequency OBJECT-TYPE
       SYNTAX     NonNegativeInteger
       UNITS      "0.1 Hertz"
       MAX-ACCESS read-only
       STATUS     current
       DESCRIPTION
               "The present input frequency."
       ::= { upsInputEntry 2 }

   upsInputVoltage OBJECT-TYPE
       SYNTAX     NonNegativeInteger
       UNITS      "RMS Volts"
       MAX-ACCESS read-only
       STATUS     current
       DESCRIPTION
               "The magnitude of the present input voltage."
       ::= { upsInputEntry 3 }

   upsInputCurrent OBJECT-TYPE
       SYNTAX     NonNegativeInteger
       UNITS      "0.1 RMS Amp"
       MAX-ACCESS read-only
       STATUS     current
       DESCRIPTION
               "The magnitude of the present input current."
       ::= { upsInputEntry 4 }

   upsInputTruePower OBJECT-TYPE
       SYNTAX     NonNegativeInteger
       UNITS      "Watts"
       MAX-ACCESS read-only
       STATUS     current
       DESCRIPTION
               "The magnitude of the present input true power."
       ::= { upsInputEntry 5 }


   --
   -- The Output group.
   --

   upsOutput             OBJECT IDENTIFIER ::= { upsObjects 4 }

   upsOutputSource OBJECT-TYPE
       SYNTAX     INTEGER {
           other(1),
           none(2),
           normal(3),
           bypass(4),
           battery(5),
           booster(6),
           reducer(7)
       }
       MAX-ACCESS read-only
       STATUS     current
       DESCRIPTION
               "The present source of output power.  The enumeration
               none(2) indicates that there is no source of output
               power (and therefore no output power), for example,
               the system has opened the output breaker."
       ::= { upsOutput 1 }

   upsOutputFrequency OBJECT-TYPE
       SYNTAX     NonNegativeInteger
       UNITS      "0.1 Hertz"
       MAX-ACCESS read-only
       STATUS     current
       DESCRIPTION
               "The present output frequency."
       ::= { upsOutput 2 }

   upsOutputNumLines OBJECT-TYPE
       SYNTAX     NonNegativeInteger
       MAX-ACCESS read-only
       STATUS     current
       DESCRIPTION
               "The number of output lines utilized in this device.
               This variable indicates the number of rows in the
               output table."
       ::= { upsOutput 3 }

   upsOutputTable OBJECT-TYPE
       SYNTAX     SEQUENCE OF UpsOutputEntry
       MAX-ACCESS not-accessible
       STATUS     current
       DESCRIPTION
               "A list of output table entries.  The number of
               entries is given by the value of upsOutputNumLines."
       ::= { upsOutput 4 }

   upsOutputEntry OBJECT-TYPE
       SYNTAX     UpsOutputEntry
       MAX-ACCESS not-accessible
       STATUS     current
       DESCRIPTION
               "An entry containing information applicable to a
               particular output line."
       INDEX { upsOutputLineIndex }
       ::= { upsOutputTable 1 }

   UpsOutputEntry ::= SEQUENCE {
       upsOutputLineIndex   PositiveInteger,
       upsOutputVoltage     NonNegativeInteger,
       upsOutputCurrent     NonNegativeInteger,
       upsOutputPower       NonNegativeInteger,
       upsOutputPercentLoad INTEGER
   }

   upsOutputLineIndex OBJECT-TYPE
       SYNTAX     PositiveInteger
       MAX-ACCESS not-accessible
       STATUS     current
       DESCRIPTION
               "The output line identifier."
       ::= { upsOutputEntry 1 }

   upsOutputVoltage OBJECT-TYPE
       SYNTAX     NonNegativeInteger
       UNITS      "RMS Volts"
       MAX-ACCESS read-only
       STATUS     current
       DESCRIPTION
               "The present output voltage."
       ::= { upsOutputEntry 2 }

   upsOutputCurrent OBJECT-TYPE
       SYNTAX     NonNegativeInteger
       UNITS      "0.1 RMS Amp"
       MAX-ACCESS read-only
       STATUS     current
       DESCRIPTION
               "The present output current."
       ::= { upsOutputEntry 3 }

   upsOutputPower OBJECT-TYPE
       SYNTAX     NonNegativeInteger
       UNITS      "Watts"
       MAX-ACCESS read-only
       STATUS     current
       DESCRIPTION
               "The present output true power."
       ::= { upsOutputEntry 4 }

   upsOutputPercentLoad OBJECT-TYPE
       SYNTAX     INTEGER (0..200)
       UNITS      "percent"
       MAX-ACCESS read-only
       STATUS     current
       DESCRIPTION
               "The percentage of the UPS power capacity presently
               being used on this output line, i.e., the greater of
               the percent load of true power capacity and the
               percent load of VA."
       ::= { upsOutputEntry 5 }



   --
   -- The Bypass group.
   --

   upsBypass             OBJECT IDENTIFIER ::= { upsObjects 5 }

   upsBypassFrequency OBJECT-TYPE
       SYNTAX     NonNegativeInteger
       UNITS      "0.1 Hertz"
       MAX-ACCESS read-only
       STATUS     current
       DESCRIPTION
               "The present bypass frequency."
       ::= { upsBypass 1 }

   upsBypassNumLines OBJECT-TYPE
       SYNTAX     NonNegativeInteger
       MAX-ACCESS read-only
       STATUS     current
       DESCRIPTION
               "The number of bypass lines utilized in this device.
               This entry indicates the number of rows in the bypass
               table."
       ::= { upsBypass 2 }

   upsBypassTable OBJECT-TYPE
       SYNTAX     SEQUENCE OF UpsBypassEntry
       MAX-ACCESS not-accessible
       STATUS     current
       DESCRIPTION
               "A list of bypass table entries.  The number of
               entries is given by the value of upsBypassNumLines."
       ::= { upsBypass 3 }

   upsBypassEntry OBJECT-TYPE
       SYNTAX     UpsBypassEntry
       MAX-ACCESS not-accessible
       STATUS     current
       DESCRIPTION
               "An entry containing information applicable to a
               particular bypass input."
       INDEX { upsBypassLineIndex }
       ::= { upsBypassTable 1 }

   UpsBypassEntry ::= SEQUENCE {
       upsBypassLineIndex  PositiveInteger,
       upsBypassVoltage    NonNegativeInteger,
       upsBypassCurrent    NonNegativeInteger,
       upsBypassPower      NonNegativeInteger
   }

   upsBypassLineIndex OBJECT-TYPE
       SYNTAX     PositiveInteger
       MAX-ACCESS not-accessible
       STATUS     current
       DESCRIPTION
               "The bypass line identifier."
       ::= { upsBypassEntry 1 }

   upsBypassVoltage OBJECT-TYPE
       SYNTAX     NonNegativeInteger
       UNITS      "RMS Volts"
       MAX-ACCESS read-only
       STATUS     current
       DESCRIPTION
               "The present bypass voltage."
       ::= { upsBypassEntry 2 }

   upsBypassCurrent OBJECT-TYPE
       SYNTAX     NonNegativeInteger
       UNITS      "0.1 RMS Amp"
       MAX-ACCESS read-only
       STATUS     current
       DESCRIPTION
               "The present bypass current."
       ::= { upsBypassEntry 3 }

   upsBypassPower OBJECT-TYPE
       SYNTAX     NonNegativeInteger
       UNITS      "Watts"
       MAX-ACCESS read-only
       STATUS     current
       DESCRIPTION
               "The present true power conveyed by the bypass."
       ::= { upsBypassEntry 4 }


   --
   -- The Alarm group.
   --

   upsAlarm              OBJECT IDENTIFIER ::= { upsObjects 6 }

   upsAlarmsPresent OBJECT-TYPE
       SYNTAX     Gauge32
       MAX-ACCESS read-only
       STATUS     current
       DESCRIPTION
               "The present number of active alarm conditions."
       ::= { upsAlarm 1 }

   upsAlarmTable OBJECT-TYPE
       SYNTAX     SEQUENCE OF UpsAlarmEntry
       MAX-ACCESS not-accessible
       STATUS     current
       DESCRIPTION
               "A list of alarm table entries.  The table contains
               zero, one, or many rows at any moment, depending upon
               the number of alarm conditions in effect.  The table
               is initially empty at agent startup.  The agent
               creates a row in the table each time a condition is
               detected and deletes that row when that condition no
               longer pertains.  The agent creates the first row with
               upsAlarmId equal to 1, and increments the value of
               upsAlarmId each time a new row is created, wrapping to
               the first free value greater than or equal to 1 when
               the maximum value of upsAlarmId would otherwise be
               exceeded.  Consequently, after multiple operations,
               the table may become sparse, e.g., containing entries
               for rows 95, 100, 101, and 203 and the entries should
               not be assumed to be in chronological order because
               upsAlarmId might have wrapped.

               Alarms are named by an AutonomousType (OBJECT
               IDENTIFIER), upsAlarmDescr, to allow a single table to
               reflect well known alarms plus alarms defined by a
               particular implementation, i.e., as documented in the
               private enterprise MIB definition for the device.  No
               two rows will have the same value of upsAlarmDescr,
               since alarms define conditions.  In order to meet this
               requirement, care should be taken in the definition of
               alarm conditions to insure that a system cannot enter
               the same condition multiple times simultaneously.

               The number of rows in the table at any given time is
               reflected by the value of upsAlarmsPresent."
       ::= { upsAlarm 2 }

   upsAlarmEntry OBJECT-TYPE
       SYNTAX     UpsAlarmEntry
       MAX-ACCESS not-accessible
       STATUS     current
       DESCRIPTION
               "An entry containing information applicable to a
               particular alarm."
       INDEX { upsAlarmId }
       ::= { upsAlarmTable 1 }

   UpsAlarmEntry ::= SEQUENCE {
       upsAlarmId          PositiveInteger,
       upsAlarmDescr       AutonomousType,
       upsAlarmTime        TimeStamp
   }

   upsAlarmId OBJECT-TYPE
       SYNTAX     PositiveInteger
       MAX-ACCESS not-accessible
       STATUS     current
       DESCRIPTION
               "A unique identifier for an alarm condition.  This
               value must remain constant."
       ::= { upsAlarmEntry 1 }

   upsAlarmDescr OBJECT-TYPE
       SYNTAX     AutonomousType
       MAX-ACCESS read-only
       STATUS     current
       DESCRIPTION
               "A reference to an alarm description object.  The
               object referenced should not be accessible, but rather
               be used to provide a unique description of the alarm
               condition."
       ::= { upsAlarmEntry 2 }

   upsAlarmTime OBJECT-TYPE
       SYNTAX     TimeStamp
       MAX-ACCESS read-only
       STATUS     current
       DESCRIPTION
               "The value of sysUpTime when the alarm condition was
               detected.  If the alarm condition was detected at the
               time of agent startup and presumably existed before
               agent startup, the value of upsAlarmTime shall equal
               0."
       ::= { upsAlarmEntry 3 }


   --
   -- Well known alarm conditions.
   --

   upsWellKnownAlarms    OBJECT IDENTIFIER ::= { upsAlarm 3 }
   upsAlarmBatteryBad OBJECT-IDENTITY
       STATUS     current
       DESCRIPTION
               "One or more batteries have been determined to require
               replacement."
       ::= { upsWellKnownAlarms  1 }

   upsAlarmOnBattery OBJECT-IDENTITY
       STATUS     current
       DESCRIPTION
               "The UPS is drawing power from the batteries."
       ::= { upsWellKnownAlarms  2 }

   upsAlarmLowBattery OBJECT-IDENTITY
       STATUS     current
       DESCRIPTION
               "The remaining battery run-time is less than or equal
               to upsConfigLowBattTime."
       ::= { upsWellKnownAlarms  3 }


   upsAlarmDepletedBattery OBJECT-IDENTITY
       STATUS     current
       DESCRIPTION
               "The UPS will be unable to sustain the present load
               when and if the utility power is lost."
       ::= { upsWellKnownAlarms  4 }

   upsAlarmTempBad OBJECT-IDENTITY
       STATUS     current
       DESCRIPTION
               "A temperature is out of tolerance."
       ::= { upsWellKnownAlarms  5 }

   upsAlarmInputBad OBJECT-IDENTITY
       STATUS     current
       DESCRIPTION
               "An input condition is out of tolerance."
       ::= { upsWellKnownAlarms  6 }

   upsAlarmOutputBad OBJECT-IDENTITY
       STATUS     current
       DESCRIPTION
               "An output condition (other than OutputOverload) is
               out of tolerance."
       ::= { upsWellKnownAlarms  7 }

   upsAlarmOutputOverload OBJECT-IDENTITY
       STATUS     current
       DESCRIPTION
               "The output load exceeds the UPS output capacity."
       ::= { upsWellKnownAlarms  8 }

   upsAlarmOnBypass OBJECT-IDENTITY
       STATUS     current
       DESCRIPTION
               "The Bypass is presently engaged on the UPS."
       ::= { upsWellKnownAlarms  9 }

   upsAlarmBypassBad OBJECT-IDENTITY
       STATUS     current
       DESCRIPTION
               "The Bypass is out of tolerance."
       ::= { upsWellKnownAlarms 10 }

   upsAlarmOutputOffAsRequested OBJECT-IDENTITY
       STATUS     current
       DESCRIPTION
               "The UPS has shutdown as requested, i.e., the output
               is off."
       ::= { upsWellKnownAlarms 11 }

   upsAlarmUpsOffAsRequested OBJECT-IDENTITY
       STATUS     current
       DESCRIPTION
               "The entire UPS has shutdown as commanded."
       ::= { upsWellKnownAlarms 12 }

   upsAlarmChargerFailed OBJECT-IDENTITY
       STATUS     current
       DESCRIPTION
               "An uncorrected problem has been detected within the
               UPS charger subsystem."
       ::= { upsWellKnownAlarms 13 }

   upsAlarmUpsOutputOff OBJECT-IDENTITY
       STATUS     current
       DESCRIPTION
               "The output of the UPS is in the off state."
       ::= { upsWellKnownAlarms 14 }

   upsAlarmUpsSystemOff OBJECT-IDENTITY
       STATUS     current
       DESCRIPTION
               "The UPS system is in the off state."
       ::= { upsWellKnownAlarms 15 }
   upsAlarmFanFailure OBJECT-IDENTITY
       STATUS     current
       DESCRIPTION
               "The failure of one or more fans in the UPS has been
               detected."
       ::= { upsWellKnownAlarms 16 }

   upsAlarmFuseFailure OBJECT-IDENTITY
       STATUS     current
       DESCRIPTION
               "The failure of one or more fuses has been detected."
       ::= { upsWellKnownAlarms 17 }

   upsAlarmGeneralFault OBJECT-IDENTITY
       STATUS     current
       DESCRIPTION
               "A general fault in the UPS has been detected."
       ::= { upsWellKnownAlarms 18 }

   upsAlarmDiagnosticTestFailed OBJECT-IDENTITY
       STATUS     current
       DESCRIPTION
               "The result of the last diagnostic test indicates a
               failure."
       ::= { upsWellKnownAlarms 19 }

   upsAlarmCommunicationsLost OBJECT-IDENTITY
       STATUS     current
       DESCRIPTION
               "A problem has been encountered in the communications
               between the agent and the UPS."
       ::= { upsWellKnownAlarms 20 }

   upsAlarmAwaitingPower OBJECT-IDENTITY
       STATUS     current
       DESCRIPTION
               "The UPS output is off and the UPS is awaiting the
               return of input power."
       ::= { upsWellKnownAlarms 21 }

   upsAlarmShutdownPending OBJECT-IDENTITY
       STATUS     current
       DESCRIPTION
               "A upsShutdownAfterDelay countdown is underway."
       ::= { upsWellKnownAlarms 22 }

   upsAlarmShutdownImminent OBJECT-IDENTITY
       STATUS     current
       DESCRIPTION
               "The UPS will turn off power to the load in less than
               5 seconds; this may be either a timed shutdown or a
               low battery shutdown."
       ::= { upsWellKnownAlarms 23 }

   upsAlarmTestInProgress OBJECT-IDENTITY
       STATUS     current
       DESCRIPTION
               "A test is in progress, as initiated and indicated by
               the Test Group.  Tests initiated via other
               implementation-specific mechanisms can indicate the
               presence of the testing in the alarm table, if
               desired, via a OBJECT-IDENTITY macro in the MIB
               document specific to that implementation and are
               outside the scope of this OBJECT-IDENTITY."
       ::= { upsWellKnownAlarms 24 }

   alarmAUXInput1 OBJECT-IDENTITY
       STATUS     current
       DESCRIPTION
               "Alarm AUX Input 1."
       ::= { upsWellKnownAlarms 25 }

   alarmAUXInput2 OBJECT-IDENTITY
       STATUS     current
       DESCRIPTION
               "Alarm AUX Input 2."
       ::= { upsWellKnownAlarms 26 }

   alarmAUXInput3 OBJECT-IDENTITY
       STATUS     current
       DESCRIPTION
               "Alarm AUX Input 3."
       ::= { upsWellKnownAlarms 27 }

   alarmAUXInput4 OBJECT-IDENTITY
       STATUS     current
       DESCRIPTION
               "Alarm AUX Input 4."
       ::= { upsWellKnownAlarms 28 }

   alarmSiteManagerDigitalInput1 OBJECT-IDENTITY
       STATUS     current
       DESCRIPTION
               "Alarm SiteManager Digital Input 1."
       ::= { upsWellKnownAlarms 29 }

   alarmSiteManagerDigitalInput2 OBJECT-IDENTITY
       STATUS     current
       DESCRIPTION
               "Alarm SiteManager Digital Input 2."
       ::= { upsWellKnownAlarms 30 }

   alarmSiteManagerDigitalInput3 OBJECT-IDENTITY
       STATUS     current
       DESCRIPTION
               "Alarm SiteManager Digital Input 3."
       ::= { upsWellKnownAlarms 31 }

   alarmSiteManagerDigitalInput4 OBJECT-IDENTITY
       STATUS     current
       DESCRIPTION
               "Alarm SiteManager Digital Input 4."
       ::= { upsWellKnownAlarms 32 }

   alarmSiteManagerDigitalInput5 OBJECT-IDENTITY
       STATUS     current
       DESCRIPTION
               "Alarm SiteManager Digital Input 5."
       ::= { upsWellKnownAlarms 33 }

   alarmSiteManagerDigitalInput6 OBJECT-IDENTITY
       STATUS     current
       DESCRIPTION
               "Alarm SiteManager Digital Input 6."
       ::= { upsWellKnownAlarms 34 }

   alarmSiteManagerDigitalInput7 OBJECT-IDENTITY
       STATUS     current
       DESCRIPTION
               "Alarm SiteManager Digital Input 7."
       ::= { upsWellKnownAlarms 35 }

   alarmSiteManagerDigitalInput8 OBJECT-IDENTITY
       STATUS     current
       DESCRIPTION
               "Alarm SiteManager Digital Input 8."
       ::= { upsWellKnownAlarms 36 }

   alarmSiteManagerAnalogInput1 OBJECT-IDENTITY
       STATUS     current
       DESCRIPTION
               "Alarm SiteManager Analog Input 1."
       ::= { upsWellKnownAlarms 37 }

   alarmSiteManagerAnalogInput2 OBJECT-IDENTITY
       STATUS     current
       DESCRIPTION
               "Alarm SiteManager Analog Input 2."
       ::= { upsWellKnownAlarms 38 }

   alarmSiteManagerAnalogInput3 OBJECT-IDENTITY
       STATUS     current
       DESCRIPTION
               "Alarm SiteManager Analog Input 3."
       ::= { upsWellKnownAlarms 39 }

   alarmSiteManagerAnalogInput4 OBJECT-IDENTITY
       STATUS     current
       DESCRIPTION
               "Alarm SiteManager Analog Input 4."
       ::= { upsWellKnownAlarms 40 }

   alarmSiteManagerAnalogInput5 OBJECT-IDENTITY
       STATUS     current
       DESCRIPTION
               "Alarm SiteManager Analog Input 5."
       ::= { upsWellKnownAlarms 41 }

   alarmSiteManagerAnalogInput6 OBJECT-IDENTITY
       STATUS     current
       DESCRIPTION
               "Alarm SiteManager Analog Input 6."
       ::= { upsWellKnownAlarms 42 }

   alarmSiteManagerAnalogInput7 OBJECT-IDENTITY
       STATUS     current
       DESCRIPTION
               "Alarm SiteManager Analog Input 7."
       ::= { upsWellKnownAlarms 43 }

   alarmSiteManagerAnalogInput8 OBJECT-IDENTITY
       STATUS     current
       DESCRIPTION
               "Alarm SiteManager Analog Input 8."
       ::= { upsWellKnownAlarms 44 }

   alarmSiteManagerMarker1 OBJECT-IDENTITY
       STATUS     current
       DESCRIPTION
               "Alarm SiteManager Marker 1."
       ::= { upsWellKnownAlarms 45 }

   alarmSiteManagerMarker2 OBJECT-IDENTITY
       STATUS     current
       DESCRIPTION
               "Alarm SiteManager Marker 2."
       ::= { upsWellKnownAlarms 46 }

   alarmSiteManagerMarker3 OBJECT-IDENTITY
       STATUS     current
       DESCRIPTION
               "Alarm SiteManager Marker 3."
       ::= { upsWellKnownAlarms 47 }

   alarmSiteManagerMarker4 OBJECT-IDENTITY
       STATUS     current
       DESCRIPTION
               "Alarm SiteManager Marker 4."
       ::= { upsWellKnownAlarms 48 }

   alarmSiteManagerMarker5 OBJECT-IDENTITY
       STATUS     current
       DESCRIPTION
               "Alarm SiteManager Marker 5."
       ::= { upsWellKnownAlarms 49 }

   alarmSiteManagerMarker6 OBJECT-IDENTITY
       STATUS     current
       DESCRIPTION
               "Alarm SiteManager Marker 6."
       ::= { upsWellKnownAlarms 50 }

   alarmSiteManagerMarker7 OBJECT-IDENTITY
       STATUS     current
       DESCRIPTION
               "Alarm SiteManager Marker 7."
       ::= { upsWellKnownAlarms 51 }

   alarmSiteManagerMarker8 OBJECT-IDENTITY
       STATUS     current
       DESCRIPTION
               "Alarm SiteManager Marker 8."
       ::= { upsWellKnownAlarms 52 }

   alarmSiteManagerOutput1 OBJECT-IDENTITY
       STATUS     current
       DESCRIPTION
               "Alarm SiteManager Output 1."
       ::= { upsWellKnownAlarms 53 }

   alarmSiteManagerOutput2 OBJECT-IDENTITY
       STATUS     current
       DESCRIPTION
               "Alarm SiteManager Output 2."
       ::= { upsWellKnownAlarms 54 }

   alarmSiteManagerOutput3 OBJECT-IDENTITY
       STATUS     current
       DESCRIPTION
               "Alarm SiteManager Output 3."
       ::= { upsWellKnownAlarms 55 }

   alarmSiteManagerOutput4 OBJECT-IDENTITY
       STATUS     current
       DESCRIPTION
               "Alarm SiteManager Output 4."
       ::= { upsWellKnownAlarms 56 }

   alarmSiteManagerOutput5 OBJECT-IDENTITY
       STATUS     current
       DESCRIPTION
               "Alarm SiteManager Output 5."
       ::= { upsWellKnownAlarms 57 }

   alarmSiteManagerOutput6 OBJECT-IDENTITY
       STATUS     current
       DESCRIPTION
               "Alarm SiteManager Output 6."
       ::= { upsWellKnownAlarms 58 }

   alarmSiteManagerOutput7 OBJECT-IDENTITY
       STATUS     current
       DESCRIPTION
               "Alarm SiteManager Output 7."
       ::= { upsWellKnownAlarms 59 }

   alarmSiteManagerOutput8 OBJECT-IDENTITY
       STATUS     current
       DESCRIPTION
               "Alarm SiteManager Output 8."
       ::= { upsWellKnownAlarms 60 }

   alarmSiteMonitor1 OBJECT-IDENTITY
       STATUS     current
       DESCRIPTION
               "Alarm SiteMonitor 1."
       ::= { upsWellKnownAlarms 61 }

   alarmSiteMonitor2 OBJECT-IDENTITY
       STATUS     current
       DESCRIPTION
               "Alarm SiteMonitor 2."
       ::= { upsWellKnownAlarms 62 }

   alarmSiteMonitor3 OBJECT-IDENTITY
       STATUS     current
       DESCRIPTION
               "Alarm SiteMonitor 3."
       ::= { upsWellKnownAlarms 63 }

   alarmSiteMonitor4 OBJECT-IDENTITY
       STATUS     current
       DESCRIPTION
               "Alarm SiteMonitor 4."
       ::= { upsWellKnownAlarms 64 }

   alarmSiteMonitor5 OBJECT-IDENTITY
       STATUS     current
       DESCRIPTION
               "Alarm SiteMonitor 5."
       ::= { upsWellKnownAlarms 65 }

   alarmSiteMonitor6 OBJECT-IDENTITY
       STATUS     current
       DESCRIPTION
               "Alarm SiteMonitor 6."
       ::= { upsWellKnownAlarms 66 }

   alarmSiteMonitor7 OBJECT-IDENTITY
       STATUS     current
       DESCRIPTION
               "Alarm SiteMonitor 7."
       ::= { upsWellKnownAlarms 67 }

   alarmSiteMonitor8 OBJECT-IDENTITY
       STATUS     current
       DESCRIPTION
               "Alarm SiteMonitor 8."
       ::= { upsWellKnownAlarms 68 }

   alarmSiteMonitor9 OBJECT-IDENTITY
       STATUS     current
       DESCRIPTION
               "Alarm SiteMonitor 9."
       ::= { upsWellKnownAlarms 69 }

   alarmSiteMonitor10 OBJECT-IDENTITY
       STATUS     current
       DESCRIPTION
               "Alarm SiteMonitor 10."
       ::= { upsWellKnownAlarms 70 }

   alarmSiteMonitor11 OBJECT-IDENTITY
       STATUS     current
       DESCRIPTION
               "Alarm SiteMonitor 11."
       ::= { upsWellKnownAlarms 71 }

   alarmSiteMonitor12 OBJECT-IDENTITY
       STATUS     current
       DESCRIPTION
               "Alarm SiteMonitor 12."
       ::= { upsWellKnownAlarms 72 }

   alarmSiteMonitor13 OBJECT-IDENTITY
       STATUS     current
       DESCRIPTION
               "Alarm SiteMonitor 13."
       ::= { upsWellKnownAlarms 73 }

   alarmSiteMonitor14 OBJECT-IDENTITY
       STATUS     current
       DESCRIPTION
               "Alarm SiteMonitor 14."
       ::= { upsWellKnownAlarms 74 }

   alarmSiteMonitor15 OBJECT-IDENTITY
       STATUS     current
       DESCRIPTION
               "Alarm SiteMonitor 15."
       ::= { upsWellKnownAlarms 75 }

   alarmSiteMonitor16 OBJECT-IDENTITY
       STATUS     current
       DESCRIPTION
               "Alarm SiteMonitor 16."
       ::= { upsWellKnownAlarms 76 }

   alarmSiteMonitor17 OBJECT-IDENTITY
       STATUS     current
       DESCRIPTION
               "Alarm SiteMonitor 17."
       ::= { upsWellKnownAlarms 77 }

   alarmSiteMonitor18 OBJECT-IDENTITY
       STATUS     current
       DESCRIPTION
               "Alarm SiteMonitor 18."
       ::= { upsWellKnownAlarms 78 }

   alarmSiteMonitor19 OBJECT-IDENTITY
       STATUS     current
       DESCRIPTION
               "Alarm SiteMonitor 19."
       ::= { upsWellKnownAlarms 79 }

   alarmSiteMonitor20 OBJECT-IDENTITY
       STATUS     current
       DESCRIPTION
               "Alarm SiteMonitor 20."
       ::= { upsWellKnownAlarms 80 }

   alarmSiteMonitor21 OBJECT-IDENTITY
       STATUS     current
       DESCRIPTION
               "Alarm SiteMonitor 21."
       ::= { upsWellKnownAlarms 81 }

   alarmSiteMonitor22 OBJECT-IDENTITY
       STATUS     current
       DESCRIPTION
               "Alarm SiteMonitor 22."
       ::= { upsWellKnownAlarms 82 }

   alarmSiteMonitor23 OBJECT-IDENTITY
       STATUS     current
       DESCRIPTION
               "Alarm SiteMonitor 23."
       ::= { upsWellKnownAlarms 83 }

   alarmSiteMonitor24 OBJECT-IDENTITY
       STATUS     current
       DESCRIPTION
               "Alarm SiteMonitor 24."
       ::= { upsWellKnownAlarms 84 }

   alarmSiteMonitor25 OBJECT-IDENTITY
       STATUS     current
       DESCRIPTION
               "Alarm SiteMonitor 25."
       ::= { upsWellKnownAlarms 85 }

   alarmSiteMonitor26 OBJECT-IDENTITY
       STATUS     current
       DESCRIPTION
               "Alarm SiteMonitor 26."
       ::= { upsWellKnownAlarms 86 }

   alarmSiteMonitor27 OBJECT-IDENTITY
       STATUS     current
       DESCRIPTION
               "Alarm SiteMonitor 27."
       ::= { upsWellKnownAlarms 87 }

   alarmSiteMonitor28 OBJECT-IDENTITY
       STATUS     current
       DESCRIPTION
               "Alarm SiteMonitor 28."
       ::= { upsWellKnownAlarms 88 }

   alarmSiteMonitor29 OBJECT-IDENTITY
       STATUS     current
       DESCRIPTION
               "Alarm SiteMonitor 29."
       ::= { upsWellKnownAlarms 89 }

   alarmSiteMonitor30 OBJECT-IDENTITY
       STATUS     current
       DESCRIPTION
               "Alarm SiteMonitor 30."
       ::= { upsWellKnownAlarms 90 }

   alarmSiteMonitor31 OBJECT-IDENTITY
       STATUS     current
       DESCRIPTION
               "Alarm SiteMonitor 31."
       ::= { upsWellKnownAlarms 91 }

   alarmSiteMonitor32 OBJECT-IDENTITY
       STATUS     current
       DESCRIPTION
               "Alarm SiteMonitor 32."
       ::= { upsWellKnownAlarms 92 }

   alarmSiteMonitor33 OBJECT-IDENTITY
       STATUS     current
       DESCRIPTION
               "Alarm SiteMonitor 33."
       ::= { upsWellKnownAlarms 93 }

   alarmSiteMonitor34 OBJECT-IDENTITY
       STATUS     current
       DESCRIPTION
               "Alarm SiteMonitor 34."
       ::= { upsWellKnownAlarms 94 }

   alarmSiteMonitor35 OBJECT-IDENTITY
       STATUS     current
       DESCRIPTION
               "Alarm SiteMonitor 35."
       ::= { upsWellKnownAlarms 95 }

   alarmSiteMonitor36 OBJECT-IDENTITY
       STATUS     current
       DESCRIPTION
               "Alarm SiteMonitor 36."
       ::= { upsWellKnownAlarms 96 }

   alarmSiteMonitor37 OBJECT-IDENTITY
       STATUS     current
       DESCRIPTION
               "Alarm SiteMonitor 37."
       ::= { upsWellKnownAlarms 97 }

   alarmSiteMonitor38 OBJECT-IDENTITY
       STATUS     current
       DESCRIPTION
               "Alarm SiteMonitor 38."
       ::= { upsWellKnownAlarms 98 }

   alarmSiteMonitor39 OBJECT-IDENTITY
       STATUS     current
       DESCRIPTION
               "Alarm SiteMonitor 39."
       ::= { upsWellKnownAlarms 99 }

   alarmSiteMonitor40 OBJECT-IDENTITY
       STATUS     current
       DESCRIPTION
               "Alarm SiteMonitor 40."
       ::= { upsWellKnownAlarms 100 }

   alarmSiteMonitor41 OBJECT-IDENTITY
       STATUS     current
       DESCRIPTION
               "Alarm SiteMonitor 41."
       ::= { upsWellKnownAlarms 101 }

   alarmSiteMonitor42 OBJECT-IDENTITY
       STATUS     current
       DESCRIPTION
               "Alarm SiteMonitor 42."
       ::= { upsWellKnownAlarms 102 }

   alarmSiteMonitor43 OBJECT-IDENTITY
       STATUS     current
       DESCRIPTION
               "Alarm SiteMonitor 43."
       ::= { upsWellKnownAlarms 103 }

   alarmSiteMonitor44 OBJECT-IDENTITY
       STATUS     current
       DESCRIPTION
               "Alarm SiteMonitor 44."
       ::= { upsWellKnownAlarms 104 }

   alarmSiteMonitor45 OBJECT-IDENTITY
       STATUS     current
       DESCRIPTION
               "Alarm SiteMonitor 45."
       ::= { upsWellKnownAlarms 105 }

   alarmSiteMonitor46 OBJECT-IDENTITY
       STATUS     current
       DESCRIPTION
               "Alarm SiteMonitor 46."
       ::= { upsWellKnownAlarms 106 }

   alarmSiteMonitor47 OBJECT-IDENTITY
       STATUS     current
       DESCRIPTION
               "Alarm SiteMonitor 47."
       ::= { upsWellKnownAlarms 107 }

   alarmSiteMonitor48 OBJECT-IDENTITY
       STATUS     current
       DESCRIPTION
               "Alarm SiteMonitor 48."
       ::= { upsWellKnownAlarms 108 }

   alarmSiteMonitor49 OBJECT-IDENTITY
       STATUS     current
       DESCRIPTION
               "Alarm SiteMonitor 49."
       ::= { upsWellKnownAlarms 109 }

   alarmSiteMonitor50 OBJECT-IDENTITY
       STATUS     current
       DESCRIPTION
               "Alarm SiteMonitor 50."
       ::= { upsWellKnownAlarms 110 }

   alarmSiteMonitor51 OBJECT-IDENTITY
       STATUS     current
       DESCRIPTION
               "Alarm SiteMonitor 51."
       ::= { upsWellKnownAlarms 111 }

   alarmSiteMonitor52 OBJECT-IDENTITY
       STATUS     current
       DESCRIPTION
               "Alarm SiteMonitor 52."
       ::= { upsWellKnownAlarms 112 }

   alarmSiteMonitor53 OBJECT-IDENTITY
       STATUS     current
       DESCRIPTION
               "Alarm SiteMonitor 53."
       ::= { upsWellKnownAlarms 113 }

   alarmSiteMonitor54 OBJECT-IDENTITY
       STATUS     current
       DESCRIPTION
               "Alarm SiteMonitor 54."
       ::= { upsWellKnownAlarms 114 }

   alarmSiteMonitor55 OBJECT-IDENTITY
       STATUS     current
       DESCRIPTION
               "Alarm SiteMonitor 55."
       ::= { upsWellKnownAlarms 115 }

   alarmSiteMonitor56 OBJECT-IDENTITY
       STATUS     current
       DESCRIPTION
               "Alarm SiteMonitor 56."
       ::= { upsWellKnownAlarms 116 }

   alarmSiteMonitor57 OBJECT-IDENTITY
       STATUS     current
       DESCRIPTION
               "Alarm SiteMonitor 57."
       ::= { upsWellKnownAlarms 117 }

   alarmSiteMonitor58 OBJECT-IDENTITY
       STATUS     current
       DESCRIPTION
               "Alarm SiteMonitor 58."
       ::= { upsWellKnownAlarms 118 }

   alarmSiteMonitor59 OBJECT-IDENTITY
       STATUS     current
       DESCRIPTION
               "Alarm SiteMonitor 59."
       ::= { upsWellKnownAlarms 119 }

   alarmSiteMonitor60 OBJECT-IDENTITY
       STATUS     current
       DESCRIPTION
               "Alarm SiteMonitor 60."
       ::= { upsWellKnownAlarms 120 }

   alarmSiteMonitor61 OBJECT-IDENTITY
       STATUS     current
       DESCRIPTION
               "Alarm SiteMonitor 61."
       ::= { upsWellKnownAlarms 121 }

   alarmSiteMonitor62 OBJECT-IDENTITY
       STATUS     current
       DESCRIPTION
               "Alarm SiteMonitor 62."
       ::= { upsWellKnownAlarms 122 }

   alarmSiteMonitor63 OBJECT-IDENTITY
       STATUS     current
       DESCRIPTION
               "Alarm SiteMonitor 63."
       ::= { upsWellKnownAlarms 123 }

   alarmSiteMonitor64 OBJECT-IDENTITY
       STATUS     current
       DESCRIPTION
               "Alarm SiteMonitor 64."
       ::= { upsWellKnownAlarms 124 }

   alarmSensorManager1Low OBJECT-IDENTITY
       STATUS     current
       DESCRIPTION
               "Alarm SensorManager sensor 1 lower threshold reached."
       ::= { upsWellKnownAlarms 125 }

   alarmSensorManager2Low OBJECT-IDENTITY
       STATUS     current
       DESCRIPTION
               "Alarm SensorManager sensor 2 lower threshold reached."
       ::= { upsWellKnownAlarms 126 }

   alarmSensorManager3Low OBJECT-IDENTITY
       STATUS     current
       DESCRIPTION
               "Alarm SensorManager sensor 3 lower threshold reached."
       ::= { upsWellKnownAlarms 127 }

   alarmSensorManager4Low OBJECT-IDENTITY
       STATUS     current
       DESCRIPTION
               "Alarm SensorManager sensor 4 lower threshold reached."
       ::= { upsWellKnownAlarms 128 }

   alarmSensorManager5Low OBJECT-IDENTITY
       STATUS     current
       DESCRIPTION
               "Alarm SensorManager sensor 5 lower threshold reached."
       ::= { upsWellKnownAlarms 129 }

   alarmSensorManager6Low OBJECT-IDENTITY
       STATUS     current
       DESCRIPTION
               "Alarm SensorManager sensor 6 lower threshold reached."
       ::= { upsWellKnownAlarms 130 }

   alarmSensorManager7Low OBJECT-IDENTITY
       STATUS     current
       DESCRIPTION
               "Alarm SensorManager sensor 7 lower threshold reached."
       ::= { upsWellKnownAlarms 131 }

   alarmSensorManager8Low OBJECT-IDENTITY
       STATUS     current
       DESCRIPTION
               "Alarm SensorManager sensor 8 lower threshold reached."
       ::= { upsWellKnownAlarms 132 }

   alarmSensorManager1High OBJECT-IDENTITY
       STATUS     current
       DESCRIPTION
               "Alarm SensorManager sensor 1 upper threshold reached."
       ::= { upsWellKnownAlarms 133 }

   alarmSensorManager2High OBJECT-IDENTITY
       STATUS     current
       DESCRIPTION
               "Alarm SensorManager sensor 2 upper threshold reached."
       ::= { upsWellKnownAlarms 134 }

   alarmSensorManager3High OBJECT-IDENTITY
       STATUS     current
       DESCRIPTION
               "Alarm SensorManager sensor 3 upper threshold reached."
       ::= { upsWellKnownAlarms 135 }

   alarmSensorManager4High OBJECT-IDENTITY
       STATUS     current
       DESCRIPTION
               "Alarm SensorManager sensor 4 upper threshold reached."
       ::= { upsWellKnownAlarms 136 }

   alarmSensorManager5High OBJECT-IDENTITY
       STATUS     current
       DESCRIPTION
               "Alarm SensorManager sensor 5 upper threshold reached."
       ::= { upsWellKnownAlarms 137 }

   alarmSensorManager6High OBJECT-IDENTITY
       STATUS     current
       DESCRIPTION
               "Alarm SensorManager sensor 6 upper threshold reached."
       ::= { upsWellKnownAlarms 138 }

   alarmSensorManager7High OBJECT-IDENTITY
       STATUS     current
       DESCRIPTION
               "Alarm SensorManager sensor 7 upper threshold reached."
       ::= { upsWellKnownAlarms 139 }

   alarmSensorManager8High OBJECT-IDENTITY
       STATUS     current
       DESCRIPTION
               "alarm SensorManager sensor 8 upper threshold reached."
       ::= { upsWellKnownAlarms 140 }

   alarmUser1 OBJECT-IDENTITY
       STATUS     current
       DESCRIPTION
               "User defined alarm."
       ::= { upsWellKnownAlarms 141 }

   alarmUser2 OBJECT-IDENTITY
       STATUS     current
       DESCRIPTION
               "User defined alarm 2."
       ::= { upsWellKnownAlarms 142 }

   alarmUser3 OBJECT-IDENTITY
       STATUS     current
       DESCRIPTION
               "User defined alarm 3."
       ::= { upsWellKnownAlarms 143 }

   alarmUser4 OBJECT-IDENTITY
       STATUS     current
       DESCRIPTION
               "User defined alarm 4."
       ::= { upsWellKnownAlarms 144 }

   alarmUser5 OBJECT-IDENTITY
       STATUS     current
       DESCRIPTION
               "User defined alarm 5."
       ::= { upsWellKnownAlarms 145 }

   alarmUser6 OBJECT-IDENTITY
       STATUS     current
       DESCRIPTION
               "User defined alarm 6."
       ::= { upsWellKnownAlarms 146 }

   alarmUser7 OBJECT-IDENTITY
       STATUS     current
       DESCRIPTION
               "User defined alarm 7."
       ::= { upsWellKnownAlarms 147 }

   statusDischarging OBJECT-IDENTITY
       STATUS     current
       DESCRIPTION
               "Discharging"
       ::= { upsWellKnownAlarms 148 }

   statusCharging OBJECT-IDENTITY
       STATUS     current
       DESCRIPTION
               "Charging"
       ::= { upsWellKnownAlarms 149 }

   alarmSensorManagerInput1 OBJECT-IDENTITY
       STATUS     current
       DESCRIPTION
               "Alarm SensorManager input 1 not normal."
       ::= { upsWellKnownAlarms 150 }

   alarmSensorManagerInput2 OBJECT-IDENTITY
       STATUS     current
       DESCRIPTION
               "Alarm SensorManager input 2 not normal."
       ::= { upsWellKnownAlarms 151 }

   alarmSensorManagerInput3 OBJECT-IDENTITY
       STATUS     current
       DESCRIPTION
               "Alarm SensorManager input 3 not normal."
       ::= { upsWellKnownAlarms 152 }

   alarmSensorManagerInput4 OBJECT-IDENTITY
       STATUS     current
       DESCRIPTION
               "Alarm SensorManager input 4 not normal."
       ::= { upsWellKnownAlarms 153 }

   alarmSensorManagerOutput1 OBJECT-IDENTITY
       STATUS     current
       DESCRIPTION
               "Alarm SensorManager output 1 not normal."
       ::= { upsWellKnownAlarms 154 }

   alarmSensorManagerOutput2 OBJECT-IDENTITY
       STATUS     current
       DESCRIPTION
               "Alarm SensorManager output 2 not normal."
       ::= { upsWellKnownAlarms 155 }

   alarmSensorManagerOutput3 OBJECT-IDENTITY
       STATUS     current
       DESCRIPTION
               "Alarm SensorManager output 3 not normal."
       ::= { upsWellKnownAlarms 156 }

   alarmSensorManagerOutput4 OBJECT-IDENTITY
       STATUS     current
       DESCRIPTION
               "Alarm SensorManager output 4 not normal."
       ::= { upsWellKnownAlarms 157 }

   alarmSensorManagerComLost OBJECT-IDENTITY
       STATUS     current
       DESCRIPTION
               "Alarm SensorManager communication lost."
       ::= { upsWellKnownAlarms 158 }

   alarmVuesWindalarm OBJECT-IDENTITY
       STATUS     current
       DESCRIPTION
               "Antennenmast Windalarm."
       ::= { upsWellKnownAlarms 159 }

   alarmTransferswitchSourcesAsynchronous OBJECT-IDENTITY
       STATUS     current
       DESCRIPTION
               "The Sources are not synchronous."
       ::= { upsWellKnownAlarms 160 }

   alarmTransferswitchStaticSwitchAFailure OBJECT-IDENTITY
       STATUS     current
       DESCRIPTION
               "The failure of static Switch A has been detected."
       ::= { upsWellKnownAlarms 161 }

   alarmTransferswitchStaticSwitchBFailure OBJECT-IDENTITY
       STATUS     current
       DESCRIPTION
               "The failure of static Switch B has been detected."
       ::= { upsWellKnownAlarms 162 }

   alarmTransferswitchOnStaticSwitchA OBJECT-IDENTITY
       STATUS     current
       DESCRIPTION
               "The static Switch A is presently engaged."
       ::= { upsWellKnownAlarms 163 }

   alarmTransferswitchOnStaticSwitchB OBJECT-IDENTITY
       STATUS     current
       DESCRIPTION
               "The static Switch B is presently engaged."
       ::= { upsWellKnownAlarms 164 }

   alarmTransferswitchOnManualBypassA OBJECT-IDENTITY
       STATUS     current
       DESCRIPTION
               "The manual Bypass A is presently engaged."
       ::= { upsWellKnownAlarms 165 }

   alarmTransferswitchOnManualBypassB OBJECT-IDENTITY
       STATUS     current
       DESCRIPTION
               "The manual Bypass B is presently engaged."
       ::= { upsWellKnownAlarms 166 }

   alarmTransferswitchSourceAFailure OBJECT-IDENTITY
       STATUS     current
       DESCRIPTION
               "The failure of static Source A has been detected."
       ::= { upsWellKnownAlarms 167 }

   alarmTransferswitchSourceBFailure OBJECT-IDENTITY
       STATUS     current
       DESCRIPTION
               "The failure of static Source B has been detected."
       ::= { upsWellKnownAlarms 168 }

   alarmTransferswitchGeneralFault OBJECT-IDENTITY
       STATUS     current
       DESCRIPTION
               "A general fault has been detected."
       ::= { upsWellKnownAlarms 169 }

   alarmTransferswitchRedundancyLost OBJECT-IDENTITY
       STATUS     current
       DESCRIPTION
               "Unable to switch to the alternate power source."
       ::= { upsWellKnownAlarms 170 }

   alarmTransferswitchOutputOverload OBJECT-IDENTITY
       STATUS     current
       DESCRIPTION
               "The output load exceeds the output capacity."
       ::= { upsWellKnownAlarms 171 }

   --
   -- The Test Group
   --

   upsTest               OBJECT IDENTIFIER ::= { upsObjects 7 }

   upsTestId OBJECT-TYPE
       SYNTAX     OBJECT IDENTIFIER
       MAX-ACCESS read-write
       STATUS     current
       DESCRIPTION
               "The test is named by an OBJECT IDENTIFIER which
               allows a standard mechanism for the initiation of
               tests, including the well known tests identified in
               this document as well as those introduced by a
               particular implementation, i.e., as documented in the
               private enterprise MIB definition for the device.

               Setting this variable initiates the named test. Sets
               to this variable require the presence of
               upsTestSpinLock in the same SNMP message.

               The set request will be rejected with an appropriate
               error message if the requested test cannot be
               performed, including attempts to start a test when
               another test is already in progress.  The status of
               the current or last test is maintained in
               upsTestResultsSummary. Tests in progress may be
               aborted by setting the upsTestId variable to
               upsTestAbortTestInProgress.

               Read operations return the value of the name of the
               test in progress if a test is in progress or the name
               of the last test performed if no test is in progress,
               unless no test has been run, in which case the well
               known value upsTestNoTestsInitiated is returned."
       ::= { upsTest 1 }

   -- see [6] for more information on the semantics of objects with
   -- syntax of TestAndIncr

   upsTestSpinLock OBJECT-TYPE
       SYNTAX     TestAndIncr
       MAX-ACCESS read-write
       STATUS     current
       DESCRIPTION
               "A spin lock on the test subsystem.  The spinlock is
               used as follows.

               Before starting a test, a manager-station should make
               sure that a test is not in progress as follows:

                   try_again:
                     get (upsTestSpinLock)
                     while (upsTestResultsSummary == inProgress) {
                       /* loop while a test is running for another
               manager */
                       short delay
                       get (upsTestSpinLock)
                     }
                     lock_value = upsTestSpinLock
                     /* no test in progress, start the test */
                     set (upsTestSpinLock = lock_value, upsTestId =
               requested_test)
                     if (error_index == 1) { /* (upsTestSpinLock
               failed) */
                       /* if problem is not access control, then
                           some other manager slipped in ahead of us
               */
                       goto try_again
                     }
                     if (error_index == 2) { /* (upsTestId) */
                       /* cannot perform the test */
                       give up
                     }
                     /* test started ok */
                     /* wait for test completion by polling
               upsTestResultsSummary */
                     get (upsTestSpinLock, upsTestResultsSummary,
               upsTestResultsDetail)
                     while (upsTestResultsSummary == inProgress) {
                       short delay
                       get (upsTestSpinLock, upsTestResultsSummary,
               upsTestResultsDetail)
                     }
                     /* when test completes, retrieve any additional
               test results */
                     /* if upsTestSpinLock == lock_value + 1, then
               these are our test */
                     /* results (as opposed to another manager's */
                     The initial value of upsTestSpinLock at agent
               initialization shall
                     be 1."
       ::= { upsTest 2 }

   upsTestResultsSummary OBJECT-TYPE
       SYNTAX     INTEGER {
           donePass(1),
           doneWarning(2),
           doneError(3),
           aborted(4),
           inProgress(5),
           noTestsInitiated(6)
       }
       MAX-ACCESS read-only
       STATUS     current
       DESCRIPTION
               "The results of the current or last UPS diagnostics
               test performed.  The values for donePass(1),
               doneWarning(2), and doneError(3) indicate that the
               test completed either successfully, with a warning, or
               with an error, respectively.  The value aborted(4) is
               returned for tests which are aborted by setting the
               value of upsTestId to upsTestAbortTestInProgress.
               Tests which have not yet concluded are indicated by
               inProgress(5).  The value noTestsInitiated(6)
               indicates that no previous test results are available,
               such as is the case when no tests have been run since
               the last reinitialization of the network management
               subsystem and the system has no provision for non-
               volatile storage of test results."
       ::= { upsTest 3 }

   upsTestResultsDetail OBJECT-TYPE
       SYNTAX     DisplayString (SIZE (0..255))
       MAX-ACCESS read-only
       STATUS     current
       DESCRIPTION
               "Additional information about upsTestResultsSummary.
               If no additional information available, a zero length
               string is returned."
       ::= { upsTest 4 }

   upsTestStartTime OBJECT-TYPE
       SYNTAX     TimeStamp
       MAX-ACCESS read-only
       STATUS     current
       DESCRIPTION
               "The value of sysUpTime at the time the test in
               progress was initiated, or, if no test is in progress,
               the time the previous test was initiated.  If the
               value of upsTestResultsSummary is noTestsInitiated(6),
               upsTestStartTime has the value 0."
       ::= { upsTest 5 }

   upsTestElapsedTime OBJECT-TYPE
       SYNTAX     TimeInterval
       MAX-ACCESS read-only
       STATUS     current
       DESCRIPTION
               "The amount of time, in TimeTicks, since the test in
               progress was initiated, or, if no test is in progress,
               the previous test took to complete.  If the value of
               upsTestResultsSummary is noTestsInitiated(6),
               upsTestElapsedTime has the value 0."
       ::= { upsTest 6 }

   --
   -- Well known tests.
   --

   upsWellKnownTests     OBJECT IDENTIFIER ::= { upsTest 7 }


   upsTestNoTestsInitiated OBJECT-IDENTITY
       STATUS     current
       DESCRIPTION
               "No tests have been initiated and no test is in
               progress."
       ::= { upsWellKnownTests  1 }

   upsTestAbortTestInProgress OBJECT-IDENTITY
       STATUS     current
       DESCRIPTION
               "The test in progress is to be aborted / the test in
               progress was aborted."
       ::= { upsWellKnownTests  2 }

   upsTestGeneralSystemsTest OBJECT-IDENTITY
       STATUS     current
       DESCRIPTION
               "The manufacturer's standard test of UPS device
               systems."
       ::= { upsWellKnownTests  3 }

   upsTestQuickBatteryTest OBJECT-IDENTITY
       STATUS     current
       DESCRIPTION
               "A test that is sufficient to determine if the battery
               needs replacement."
       ::= { upsWellKnownTests  4 }

   upsTestDeepBatteryCalibration OBJECT-IDENTITY
       STATUS     current
       DESCRIPTION
               "The system is placed on battery to a discharge level,
               set by the manufacturer, sufficient to determine
               battery replacement and battery run-time with a high
               degree of confidence.  WARNING:  this test will leave
               the battery in a low charge state and will require
               time for recharging to a level sufficient to provide
               normal battery duration for the protected load."
       ::= { upsWellKnownTests  5 }


   --
   -- The Control group.
   --

   upsControl            OBJECT IDENTIFIER ::= { upsObjects 8 }

   upsShutdownType OBJECT-TYPE
       SYNTAX     INTEGER {
           output(1),
           system(2)
       }
       MAX-ACCESS read-write
       STATUS     current
       DESCRIPTION
               "This object determines the nature of the action to be
               taken at the time when the countdown of the
               upsShutdownAfterDelay and upsRebootWithDuration
               objects reaches zero.

               Setting this object to output(1) indicates that
               shutdown requests should cause only the output of the
               UPS to turn off.  Setting this object to system(2)
               indicates that shutdown requests will cause the entire
               UPS system to turn off."
       ::= { upsControl 1 }

   upsShutdownAfterDelay OBJECT-TYPE
       SYNTAX     INTEGER (-1..2147483648)
       UNITS      "seconds"
       MAX-ACCESS read-write
       STATUS     current
       DESCRIPTION
               "Setting this object will shutdown (i.e., turn off)
               either the UPS output or the UPS system (as determined
               by the value of upsShutdownType at the time of
               shutdown) after the indicated number of seconds, or
               less if the UPS batteries become depleted. Setting
               this object to 0 will cause the shutdown to occur
               immediately.  Setting this object to -1 will abort the
               countdown.  If the system is already in the desired
               state at the time the countdown reaches 0, then
               nothing will happen.  That is, there is no additional
               action at that time if upsShutdownType = system and
               the system is already off.  Similarly, there is no
               additional action at that time if upsShutdownType =
               output and the output is already off.  When read,
               upsShutdownAfterDelay will return the number of
               seconds remaining until shutdown, or -1 if no shutdown
               countdown is in effect.  On some systems, if the agent
               is restarted while a shutdown countdown is in effect,
               the countdown may be aborted.  Sets to this object
               override any upsShutdownAfterDelay already in effect."
       ::= { upsControl 2 }

   upsStartupAfterDelay OBJECT-TYPE
       SYNTAX     INTEGER (-1..2147483648)
       UNITS      "seconds"
       MAX-ACCESS read-write
       STATUS     current
       DESCRIPTION
               "Setting this object will start the output after the
               indicated number of seconds, including starting the
               UPS, if necessary.  Setting this object to 0 will
               cause the startup to occur immediately.  Setting this
               object to -1 will abort the countdown.  If the output
               is already on at the time the countdown reaches 0,
               then nothing will happen.  Sets to this object
               override the effect of any upsStartupAfterDelay
               countdown or upsRebootWithDuration countdown in
               progress.  When read, upsStartupAfterDelay will return
               the number of seconds until startup, or -1 if no
               startup countdown is in effect.  If the countdown
               expires during a utility failure, the startup shall
               not occur until the utility power is restored.  On
               some systems, if the agent is restarted while a
               startup countdown is in effect, the countdown is
               aborted."
       ::= { upsControl 3 }

   upsRebootWithDuration OBJECT-TYPE
       SYNTAX     INTEGER (-1..300)
       UNITS      "seconds"
       MAX-ACCESS read-write
       STATUS     current
       DESCRIPTION
               "Setting this object will immediately shutdown (i.e.,
               turn off) either the UPS output or the UPS system (as
               determined by the value of upsShutdownType at the time
               of shutdown) for a period equal to the indicated
               number of seconds, after which time the output will be
               started, including starting the UPS, if necessary.  If
               the number of seconds required to perform the request
               is greater than the requested duration, then the
               requested shutdown and startup cycle shall be
               performed in the minimum time possible, but in no case
               shall this require more than the requested duration
               plus 60 seconds.  When read, upsRebootWithDuration
               shall return the number of seconds remaining in the
               countdown, or -1 if no countdown is in progress.  If
               the startup should occur during a utility failure, the
               startup shall not occur until the utility power is
               restored."
       ::= { upsControl 4 }

   upsAutoRestart OBJECT-TYPE
       SYNTAX     INTEGER {
           on(1),
           off(2)
       }
       MAX-ACCESS read-write
       STATUS     current
       DESCRIPTION
               "Setting this object to 'on' will cause the UPS system
               to restart after a shutdown if the shutdown occurred
               during a power loss as a result of either a
               upsShutdownAfterDelay or an internal battery depleted
               condition.  Setting this object to 'off' will prevent
               the UPS system from restarting after a shutdown until
               an operator manually or remotely explicitly restarts
               it.  If the UPS is in a startup or reboot countdown,
               then the UPS will not restart until that delay has
               been satisfied."
       ::= { upsControl 5 }


   --
   -- The Configuration group.
   --

   upsConfig             OBJECT IDENTIFIER ::= { upsObjects 9 }

   upsConfigInputVoltage OBJECT-TYPE
       SYNTAX     NonNegativeInteger
       UNITS      "RMS Volts"
       MAX-ACCESS read-write
       STATUS     current
       DESCRIPTION
               "The magnitude of the nominal input voltage.  On those
               systems which support read-write access to this
               object, if there is an attempt to set this variable to
               a value that is not supported, the request must be
               rejected and the agent shall respond with an
               appropriate error message, i.e., badValue for SNMPv1,
               or inconsistentValue for SNMPv2."
       ::= { upsConfig 1 }

   upsConfigInputFreq OBJECT-TYPE
       SYNTAX     NonNegativeInteger
       UNITS      "0.1 Hertz"
       MAX-ACCESS read-write
       STATUS     current
       DESCRIPTION
               "The nominal input frequency.  On those systems which
               support read-write access to this object, if there is
               an attempt to set this variable to a value that is not
               supported, the request must be rejected and the agent
               shall respond with an appropriate error message, i.e.,
               badValue for SNMPv1, or inconsistentValue for SNMPv2."
       ::= { upsConfig 2 }

   upsConfigOutputVoltage OBJECT-TYPE
       SYNTAX     NonNegativeInteger
       UNITS      "RMS Volts"
       MAX-ACCESS read-write
       STATUS     current
       DESCRIPTION
               "The magnitude of the nominal output voltage.  On
               those systems which support read-write access to this
               object, if there is an attempt to set this variable to
               a value that is not supported, the request must be
               rejected and the agent shall respond with an
               appropriate error message, i.e., badValue for SNMPv1,
               or inconsistentValue for SNMPv2."
       ::= { upsConfig 3 }

   upsConfigOutputFreq OBJECT-TYPE
       SYNTAX     NonNegativeInteger
       UNITS      "0.1 Hertz"
       MAX-ACCESS read-write
       STATUS     current
       DESCRIPTION
               "The nominal output frequency.  On those systems which
               support read-write access to this object, if there is
               an attempt to set this variable to a value that is not
               supported, the request must be rejected and the agent
               shall respond with an appropriate error message, i.e.,
               badValue for SNMPv1, or inconsistentValue for SNMPv2."
       ::= { upsConfig 4 }

   upsConfigOutputVA OBJECT-TYPE
       SYNTAX     NonNegativeInteger
       UNITS      "Volt-Amps"
       MAX-ACCESS read-only
       STATUS     current
       DESCRIPTION
               "The magnitude of the nominal Volt-Amp rating."
       ::= { upsConfig 5 }

   upsConfigOutputPower OBJECT-TYPE
       SYNTAX     NonNegativeInteger
       UNITS      "Watts"
       MAX-ACCESS read-only
       STATUS     current
       DESCRIPTION
               "The magnitude of the nominal true power rating."
       ::= { upsConfig 6 }

   upsConfigLowBattTime OBJECT-TYPE
       SYNTAX     NonNegativeInteger
       UNITS      "minutes"
       MAX-ACCESS read-write
       STATUS     current
       DESCRIPTION
               "The value of upsEstimatedMinutesRemaining at which a
               lowBattery condition is declared.  For agents which
               support only discrete (discontinuous) values, then the
               agent shall round up to the next supported value.  If
               the requested value is larger than the largest
               supported value, then the largest supported value
               shall be selected."
       ::= { upsConfig 7 }

   upsConfigAudibleStatus OBJECT-TYPE
       SYNTAX     INTEGER {
           disabled(1),
           enabled(2),
           muted(3)
       }
       MAX-ACCESS read-write
       STATUS     current
       DESCRIPTION
               "The requested state of the audible alarm.  When in
               the disabled state, the audible alarm should never
               sound.  The enabled state is self-describing.  Setting
               this object to muted(3) when the audible alarm is
               sounding shall temporarily silence the alarm.  It will
               remain muted until it would normally stop sounding and
               the value returned for read operations during this
               period shall equal muted(3).  At the end of this
               period, the value shall revert to enabled(2).  Writes
               of the value muted(3) when the audible alarm is not
               sounding shall be accepted but otherwise shall have no
               effect."
       ::= { upsConfig 8 }

   upsConfigLowVoltageTransferPoint OBJECT-TYPE
       SYNTAX     NonNegativeInteger
       UNITS      "RMS Volts"
       MAX-ACCESS read-write
       STATUS     current
       DESCRIPTION
               "The minimum input line voltage allowed before the UPS
               system transfers to battery backup."
       ::= { upsConfig 9 }

   upsConfigHighVoltageTransferPoint OBJECT-TYPE
       SYNTAX     NonNegativeInteger
       UNITS      "RMS Volts"
       MAX-ACCESS read-write
       STATUS     current
       DESCRIPTION
               "The maximum line voltage allowed before the UPS
               system transfers to battery backup."
       ::= { upsConfig 10 }

   --
   -- The Dioad group.
   --
   sitemanager  OBJECT IDENTIFIER ::= { upsObjects 10 }
   relais       OBJECT IDENTIFIER ::= { sitemanager 1 }

   relais1 OBJECT-TYPE
       SYNTAX     INTEGER {
           off(0),
           on(1)
       }
       MAX-ACCESS read-write
       STATUS     current
       DESCRIPTION
               "Relais 1"
       ::= { relais 1 }

   relais2 OBJECT-TYPE
       SYNTAX     INTEGER {
           off(0),
           on(1)
       }
       MAX-ACCESS read-write
       STATUS     current
       DESCRIPTION
               "Relais 2"
       ::= { relais 2 }

   relais3 OBJECT-TYPE
       SYNTAX     INTEGER {
           off(0),
           on(1)
       }
       MAX-ACCESS read-write
       STATUS     current
       DESCRIPTION
               "Relais 3"
       ::= { relais 3 }

   relais4 OBJECT-TYPE
       SYNTAX     INTEGER {
           off(0),
           on(1)
       }
       MAX-ACCESS read-write
       STATUS     current
       DESCRIPTION
               "Relais 4"
       ::= { relais 4 }

   relais5 OBJECT-TYPE
       SYNTAX     INTEGER {
           off(0),
           on(1)
       }
       MAX-ACCESS read-write
       STATUS     current
       DESCRIPTION
               "Relais 5"
       ::= { relais 5 }

   relais6 OBJECT-TYPE
       SYNTAX     INTEGER {
           off(0),
           on(1)
       }
       MAX-ACCESS read-write
       STATUS     current
       DESCRIPTION
               "Relais 6"
       ::= { relais 6 }

   relais7 OBJECT-TYPE
       SYNTAX     INTEGER {
           off(0),
           on(1)
       }
       MAX-ACCESS read-write
       STATUS     current
       DESCRIPTION
               "Relais 7"
       ::= { relais 7 }

   relais8 OBJECT-TYPE
       SYNTAX     INTEGER {
           off(0),
           on(1)
       }
       MAX-ACCESS read-write
       STATUS     current
       DESCRIPTION
               "Relais 8"
       ::= { relais 8 }

   digital       OBJECT IDENTIFIER ::= { sitemanager 2 }

   digital1 OBJECT-TYPE
       SYNTAX     INTEGER {
           off(0),
           on(1)
       }
       MAX-ACCESS read-only
       STATUS     current
       DESCRIPTION
               "Digital 1"
       ::= { digital 1 }

   digital2 OBJECT-TYPE
       SYNTAX     INTEGER {
           off(0),
           on(1)
       }
       MAX-ACCESS read-only
       STATUS     current
       DESCRIPTION
               "Digital 2"
       ::= { digital 2 }

   digital3 OBJECT-TYPE
       SYNTAX     INTEGER {
           off(0),
           on(1)
       }
       MAX-ACCESS read-only
       STATUS     current
       DESCRIPTION
               "Digital 3"
       ::= { digital 3 }

   digital4 OBJECT-TYPE
       SYNTAX     INTEGER {
           off(0),
           on(1)
       }
       MAX-ACCESS read-only
       STATUS     current
       DESCRIPTION
               "Digital 4"
       ::= { digital 4 }

   digital5 OBJECT-TYPE
       SYNTAX     INTEGER {
           off(0),
           on(1)
       }
       MAX-ACCESS read-only
       STATUS     current
       DESCRIPTION
               "Digital 5"
       ::= { digital 5 }

   digital6 OBJECT-TYPE
       SYNTAX     INTEGER {
           off(0),
           on(1)
       }
       MAX-ACCESS read-only
       STATUS     current
       DESCRIPTION
               "Digital 6"
       ::= { digital 6 }

   digital7 OBJECT-TYPE
       SYNTAX     INTEGER {
           off(0),
           on(1)
       }
       MAX-ACCESS read-only
       STATUS     current
       DESCRIPTION
               "Digital 7"
       ::= { digital 7 }

   digital8 OBJECT-TYPE
       SYNTAX     INTEGER {
           off(0),
           on(1)
       }
       MAX-ACCESS read-only
       STATUS     current
       DESCRIPTION
               "Digital 8"
       ::= { digital 8 }

   analog       OBJECT IDENTIFIER ::= { sitemanager 3 }

   analog1 OBJECT-TYPE
       SYNTAX     INTEGER
       UNITS      "degrees centigrade"
       MAX-ACCESS read-only
       STATUS     current
       DESCRIPTION
               "Analog 1"
       ::= { analog 1 }

   analog1Min OBJECT-TYPE
       SYNTAX     INTEGER
       UNITS      "degrees centigrade"
       MAX-ACCESS read-write
       STATUS     current
       DESCRIPTION
               "Analog 1 Minimum"
       ::= { analog 2 }

   analog1Max OBJECT-TYPE
       SYNTAX     INTEGER
       UNITS      "degrees centigrade"
       MAX-ACCESS read-write
       STATUS     current
       DESCRIPTION
               "Analog 1 Maximum"
       ::= { analog 3 }

   analog2 OBJECT-TYPE
       SYNTAX     INTEGER
       UNITS      "degrees centigrade"
       MAX-ACCESS read-only
       STATUS     current
       DESCRIPTION
               "Analog 2"
       ::= { analog 4 }

   analog2Min OBJECT-TYPE
       SYNTAX     INTEGER
       UNITS      "degrees centigrade"
       MAX-ACCESS read-write
       STATUS     current
       DESCRIPTION
               "Analog 2 Minimum"
       ::= { analog 5 }

   analog2Max OBJECT-TYPE
       SYNTAX     INTEGER
       UNITS      "degrees centigrade"
       MAX-ACCESS read-write
       STATUS     current
       DESCRIPTION
               "Analog 2 Maximum"
       ::= { analog 6 }

   analog3 OBJECT-TYPE
       SYNTAX     INTEGER
       UNITS      "Humidity in per mil"
       MAX-ACCESS read-only
       STATUS     current
       DESCRIPTION
               "Analog 3"
       ::= { analog 7 }

   analog3Min OBJECT-TYPE
       SYNTAX     INTEGER
       UNITS      "Humidity in per mil"
       MAX-ACCESS read-write
       STATUS     current
       DESCRIPTION
               "Analog 3 Minimum"
       ::= { analog 8 }

   analog3Max OBJECT-TYPE
       SYNTAX     INTEGER
       UNITS      "Humidity in per mil"
       MAX-ACCESS read-write
       STATUS     current
       DESCRIPTION
               "Analog 3 Maximum"
       ::= { analog 9 }

   analog4 OBJECT-TYPE
       SYNTAX     INTEGER
       UNITS      "Humidity in per mil"
       MAX-ACCESS read-only
       STATUS     current
       DESCRIPTION
               "Analog 4"
       ::= { analog 10 }

   analog4Min OBJECT-TYPE
       SYNTAX     INTEGER
       UNITS      "Humidity in per mil"
       MAX-ACCESS read-write
       STATUS     current
       DESCRIPTION
               "Analog 4 Minimum"
       ::= { analog 11 }

   analog4Max OBJECT-TYPE
       SYNTAX     INTEGER
       UNITS      "Humidity in per mil"
       MAX-ACCESS read-write
       STATUS     current
       DESCRIPTION
               "Analog 4 Maximum"
       ::= { analog 12 }

   analog5 OBJECT-TYPE
       SYNTAX     INTEGER
       UNITS      "0.1 units"
       MAX-ACCESS read-only
       STATUS     current
       DESCRIPTION
               "Analog 5"
       ::= { analog 13 }

   analog5Min OBJECT-TYPE
       SYNTAX     INTEGER
       UNITS      "0.1 units"
       MAX-ACCESS read-write
       STATUS     current
       DESCRIPTION
               "Analog 5 Minimum"
       ::= { analog 14 }

   analog5Max OBJECT-TYPE
       SYNTAX     INTEGER
       UNITS      "0.1 units"
       MAX-ACCESS read-write
       STATUS     current
       DESCRIPTION
               "Analog 5 Maximum"
       ::= { analog 15 }

   analog6 OBJECT-TYPE
       SYNTAX     INTEGER
       UNITS      "0.1 units"
       MAX-ACCESS read-only
       STATUS     current
       DESCRIPTION
               "Analog 6"
       ::= { analog 16 }

   analog6Min OBJECT-TYPE
       SYNTAX     INTEGER
       UNITS      "0.1 units"
       MAX-ACCESS read-write
       STATUS     current
       DESCRIPTION
               "Analog 6 Minimum"
       ::= { analog 17 }

   analog6Max OBJECT-TYPE
       SYNTAX     INTEGER
       UNITS      "0.1 units"
       MAX-ACCESS read-write
       STATUS     current
       DESCRIPTION
               "Analog 6 Maximum"
       ::= { analog 18 }

   analog7 OBJECT-TYPE
       SYNTAX     INTEGER
       UNITS      "0.1 units"
       MAX-ACCESS read-only
       STATUS     current
       DESCRIPTION
               "Analog 7"
       ::= { analog 19 }

   analog7Min OBJECT-TYPE
       SYNTAX     INTEGER
       UNITS      "0.1 units"
       MAX-ACCESS read-write
       STATUS     current
       DESCRIPTION
               "Analog 7 Minimum"
       ::= { analog 20 }

   analog7Max OBJECT-TYPE
       SYNTAX     INTEGER
       UNITS      "0.1 units"
       MAX-ACCESS read-write
       STATUS     current
       DESCRIPTION
               "Analog 7 Maximum"
       ::= { analog 21 }

   analog8 OBJECT-TYPE
       SYNTAX     INTEGER
       UNITS      "0.1 units"
       MAX-ACCESS read-only
       STATUS     current
       DESCRIPTION
               "Analog 8"
       ::= { analog 22 }

   analog8Min OBJECT-TYPE
       SYNTAX     INTEGER
       UNITS      "0.1 units"
       MAX-ACCESS read-write
       STATUS     current
       DESCRIPTION
               "Analog 8 Minimum"
       ::= { analog 23 }

   analog8Max OBJECT-TYPE
       SYNTAX     INTEGER
       UNITS      "0.1 units"
       MAX-ACCESS read-write
       STATUS     current
       DESCRIPTION
               "Analog 8 Maximum"
       ::= { analog 24 }

   marker       OBJECT IDENTIFIER ::= { sitemanager 4 }

   marker1 OBJECT-TYPE
       SYNTAX     INTEGER {
           off(0),
           on(1)
       }
       MAX-ACCESS read-only
       STATUS     current
       DESCRIPTION
               "Marker 1"
       ::= { marker 1 }

   marker2 OBJECT-TYPE
       SYNTAX     INTEGER {
           off(0),
           on(1)
       }
       MAX-ACCESS read-only
       STATUS     current
       DESCRIPTION
               "Marker 2"
       ::= { marker 2 }

   marker3 OBJECT-TYPE
       SYNTAX     INTEGER {
           off(0),
           on(1)
       }
       MAX-ACCESS read-only
       STATUS     current
       DESCRIPTION
               "Marker 3"
       ::= { marker 3 }

   marker4 OBJECT-TYPE
       SYNTAX     INTEGER {
           off(0),
           on(1)
       }
       MAX-ACCESS read-only
       STATUS     current
       DESCRIPTION
               "Marker 4"
       ::= { marker 4 }

   marker5 OBJECT-TYPE
       SYNTAX     INTEGER {
           off(0),
           on(1)
       }
       MAX-ACCESS read-only
       STATUS     current
       DESCRIPTION
               "Marker 5"
       ::= { marker 5 }

   marker6 OBJECT-TYPE
       SYNTAX     INTEGER {
           off(0),
           on(1)
       }
       MAX-ACCESS read-only
       STATUS     current
       DESCRIPTION
               "Marker 6"
       ::= { marker 6 }

   marker7 OBJECT-TYPE
       SYNTAX     INTEGER {
           off(0),
           on(1)
       }
       MAX-ACCESS read-only
       STATUS     current
       DESCRIPTION
               "Marker 7"
       ::= { marker 7 }

   marker8 OBJECT-TYPE
       SYNTAX     INTEGER {
           off(0),
           on(1)
       }
       MAX-ACCESS read-only
       STATUS     current
       DESCRIPTION
               "Marker 8"
       ::= { marker 8 }

   siteMonitor       OBJECT IDENTIFIER ::= { sitemanager 5 }

   siteMonitor1 OBJECT-TYPE
       SYNTAX     INTEGER {
           off(0),
           on(1)
       }
       MAX-ACCESS read-only
       STATUS     current
       DESCRIPTION
               "SiteMonitor 1"
       ::= { siteMonitor 1 }

   siteMonitor2 OBJECT-TYPE
       SYNTAX     INTEGER {
           off(0),
           on(1)
       }
       MAX-ACCESS read-only
       STATUS     current
       DESCRIPTION
               "SiteMonitor 2"
       ::= { siteMonitor 2 }

   siteMonitor3 OBJECT-TYPE
       SYNTAX     INTEGER {
           off(0),
           on(1)
       }
       MAX-ACCESS read-only
       STATUS     current
       DESCRIPTION
               "SiteMonitor 3"
       ::= { siteMonitor 3 }

   siteMonitor4 OBJECT-TYPE
       SYNTAX     INTEGER {
           off(0),
           on(1)
       }
       MAX-ACCESS read-only
       STATUS     current
       DESCRIPTION
               "SiteMonitor 4"
       ::= { siteMonitor 4 }

   siteMonitor5 OBJECT-TYPE
       SYNTAX     INTEGER {
           off(0),
           on(1)
       }
       MAX-ACCESS read-only
       STATUS     current
       DESCRIPTION
               "SiteMonitor 5"
       ::= { siteMonitor 5 }

   siteMonitor6 OBJECT-TYPE
       SYNTAX     INTEGER {
           off(0),
           on(1)
       }
       MAX-ACCESS read-only
       STATUS     current
       DESCRIPTION
               "SiteMonitor 6"
       ::= { siteMonitor 6 }

   siteMonitor7 OBJECT-TYPE
       SYNTAX     INTEGER {
           off(0),
           on(1)
       }
       MAX-ACCESS read-only
       STATUS     current
       DESCRIPTION
               "SiteMonitor 7"
       ::= { siteMonitor 7 }

   siteMonitor8 OBJECT-TYPE
       SYNTAX     INTEGER {
           off(0),
           on(1)
       }
       MAX-ACCESS read-only
       STATUS     current
       DESCRIPTION
               "SiteMonitor 8"
       ::= { siteMonitor 8 }

   siteMonitor9 OBJECT-TYPE
       SYNTAX     INTEGER {
           off(0),
           on(1)
       }
       MAX-ACCESS read-only
       STATUS     current
       DESCRIPTION
               "SiteMonitor 9"
       ::= { siteMonitor 9 }

   siteMonitor10 OBJECT-TYPE
       SYNTAX     INTEGER {
           off(0),
           on(1)
       }
       MAX-ACCESS read-only
       STATUS     current
       DESCRIPTION
               "SiteMonitor 10"
       ::= { siteMonitor 10 }

   siteMonitor11 OBJECT-TYPE
       SYNTAX     INTEGER {
           off(0),
           on(1)
       }
       MAX-ACCESS read-only
       STATUS     current
       DESCRIPTION
               "SiteMonitor 11"
       ::= { siteMonitor 11 }

   siteMonitor12 OBJECT-TYPE
       SYNTAX     INTEGER {
           off(0),
           on(1)
       }
       MAX-ACCESS read-only
       STATUS     current
       DESCRIPTION
               "SiteMonitor 12"
       ::= { siteMonitor 12 }

   siteMonitor13 OBJECT-TYPE
       SYNTAX     INTEGER {
           off(0),
           on(1)
       }
       MAX-ACCESS read-only
       STATUS     current
       DESCRIPTION
               "SiteMonitor 13"
       ::= { siteMonitor 13 }

   siteMonitor14 OBJECT-TYPE
       SYNTAX     INTEGER {
           off(0),
           on(1)
       }
       MAX-ACCESS read-only
       STATUS     current
       DESCRIPTION
               "SiteMonitor 14"
       ::= { siteMonitor 14 }

   siteMonitor15 OBJECT-TYPE
       SYNTAX     INTEGER {
           off(0),
           on(1)
       }
       MAX-ACCESS read-only
       STATUS     current
       DESCRIPTION
               "SiteMonitor 15"
       ::= { siteMonitor 15 }

   siteMonitor16 OBJECT-TYPE
       SYNTAX     INTEGER {
           off(0),
           on(1)
       }
       MAX-ACCESS read-only
       STATUS     current
       DESCRIPTION
               "SiteMonitor 16"
       ::= { siteMonitor 16 }

   siteMonitor17 OBJECT-TYPE
       SYNTAX     INTEGER {
           off(0),
           on(1)
       }
       MAX-ACCESS read-only
       STATUS     current
       DESCRIPTION
               "SiteMonitor 17"
       ::= { siteMonitor 17 }

   siteMonitor18 OBJECT-TYPE
       SYNTAX     INTEGER {
           off(0),
           on(1)
       }
       MAX-ACCESS read-only
       STATUS     current
       DESCRIPTION
               "SiteMonitor 18"
       ::= { siteMonitor 18 }

   siteMonitor19 OBJECT-TYPE
       SYNTAX     INTEGER {
           off(0),
           on(1)
       }
       MAX-ACCESS read-only
       STATUS     current
       DESCRIPTION
               "SiteMonitor 19"
       ::= { siteMonitor 19 }

   siteMonitor20 OBJECT-TYPE
       SYNTAX     INTEGER {
           off(0),
           on(1)
       }
       MAX-ACCESS read-only
       STATUS     current
       DESCRIPTION
               "SiteMonitor 20"
       ::= { siteMonitor 20 }

   siteMonitor21 OBJECT-TYPE
       SYNTAX     INTEGER {
           off(0),
           on(1)
       }
       MAX-ACCESS read-only
       STATUS     current
       DESCRIPTION
               "SiteMonitor 21"
       ::= { siteMonitor 21 }

   siteMonitor22 OBJECT-TYPE
       SYNTAX     INTEGER {
           off(0),
           on(1)
       }
       MAX-ACCESS read-only
       STATUS     current
       DESCRIPTION
               "SiteMonitor 22"
       ::= { siteMonitor 22 }

   siteMonitor23 OBJECT-TYPE
       SYNTAX     INTEGER {
           off(0),
           on(1)
       }
       MAX-ACCESS read-only
       STATUS     current
       DESCRIPTION
               "SiteMonitor 23"
       ::= { siteMonitor 23 }

   siteMonitor24 OBJECT-TYPE
       SYNTAX     INTEGER {
           off(0),
           on(1)
       }
       MAX-ACCESS read-only
       STATUS     current
       DESCRIPTION
               "SiteMonitor 24"
       ::= { siteMonitor 24 }

   siteMonitor25 OBJECT-TYPE
       SYNTAX     INTEGER {
           off(0),
           on(1)
       }
       MAX-ACCESS read-only
       STATUS     current
       DESCRIPTION
               "SiteMonitor 25"
       ::= { siteMonitor 25 }

   siteMonitor26 OBJECT-TYPE
       SYNTAX     INTEGER {
           off(0),
           on(1)
       }
       MAX-ACCESS read-only
       STATUS     current
       DESCRIPTION
               "SiteMonitor 26"
       ::= { siteMonitor 26 }

   siteMonitor27 OBJECT-TYPE
       SYNTAX     INTEGER {
           off(0),
           on(1)
       }
       MAX-ACCESS read-only
       STATUS     current
       DESCRIPTION
               "SiteMonitor 27"
       ::= { siteMonitor 27 }

   siteMonitor28 OBJECT-TYPE
       SYNTAX     INTEGER {
           off(0),
           on(1)
       }
       MAX-ACCESS read-only
       STATUS     current
       DESCRIPTION
               "SiteMonitor 28"
       ::= { siteMonitor 28 }

   siteMonitor29 OBJECT-TYPE
       SYNTAX     INTEGER {
           off(0),
           on(1)
       }
       MAX-ACCESS read-only
       STATUS     current
       DESCRIPTION
               "SiteMonitor 29"
       ::= { siteMonitor 29 }

   siteMonitor30 OBJECT-TYPE
       SYNTAX     INTEGER {
           off(0),
           on(1)
       }
       MAX-ACCESS read-only
       STATUS     current
       DESCRIPTION
               "SiteMonitor 30"
       ::= { siteMonitor 30 }

   siteMonitor31 OBJECT-TYPE
       SYNTAX     INTEGER {
           off(0),
           on(1)
       }
       MAX-ACCESS read-only
       STATUS     current
       DESCRIPTION
               "SiteMonitor 31"
       ::= { siteMonitor 31 }

   siteMonitor32 OBJECT-TYPE
       SYNTAX     INTEGER {
           off(0),
           on(1)
       }
       MAX-ACCESS read-only
       STATUS     current
       DESCRIPTION
               "SiteMonitor 32"
       ::= { siteMonitor 32 }

   siteMonitor33 OBJECT-TYPE
       SYNTAX     INTEGER {
           off(0),
           on(1)
       }
       MAX-ACCESS read-only
       STATUS     current
       DESCRIPTION
               "SiteMonitor 33"
       ::= { siteMonitor 33 }

   siteMonitor34 OBJECT-TYPE
       SYNTAX     INTEGER {
           off(0),
           on(1)
       }
       MAX-ACCESS read-only
       STATUS     current
       DESCRIPTION
               "SiteMonitor 34"
       ::= { siteMonitor 34 }

   siteMonitor35 OBJECT-TYPE
       SYNTAX     INTEGER {
           off(0),
           on(1)
       }
       MAX-ACCESS read-only
       STATUS     current
       DESCRIPTION
               "siteMonitor 35"
       ::= { siteMonitor 35 }

   siteMonitor36 OBJECT-TYPE
       SYNTAX     INTEGER {
           off(0),
           on(1)
       }
       MAX-ACCESS read-only
       STATUS     current
       DESCRIPTION
               "SiteMonitor 36"
       ::= { siteMonitor 36 }

   siteMonitor37 OBJECT-TYPE
       SYNTAX     INTEGER {
           off(0),
           on(1)
       }
       MAX-ACCESS read-only
       STATUS     current
       DESCRIPTION
               "SiteMonitor 37"
       ::= { siteMonitor 37 }

   siteMonitor38 OBJECT-TYPE
       SYNTAX     INTEGER {
           off(0),
           on(1)
       }
       MAX-ACCESS read-only
       STATUS     current
       DESCRIPTION
               "SiteMonitor 38"
       ::= { siteMonitor 38 }

   siteMonitor39 OBJECT-TYPE
       SYNTAX     INTEGER {
           off(0),
           on(1)
       }
       MAX-ACCESS read-only
       STATUS     current
       DESCRIPTION
               "SiteMonitor 39"
       ::= { siteMonitor 39 }

   siteMonitor40 OBJECT-TYPE
       SYNTAX     INTEGER {
           off(0),
           on(1)
       }
       MAX-ACCESS read-only
       STATUS     current
       DESCRIPTION
               "SiteMonitor 40"
       ::= { siteMonitor 40 }

   siteMonitor41 OBJECT-TYPE
       SYNTAX     INTEGER {
           off(0),
           on(1)
       }
       MAX-ACCESS read-only
       STATUS     current
       DESCRIPTION
               "SiteMonitor 41"
       ::= { siteMonitor 41 }

   siteMonitor42 OBJECT-TYPE
       SYNTAX     INTEGER {
           off(0),
           on(1)
       }
       MAX-ACCESS read-only
       STATUS     current
       DESCRIPTION
               "SiteMonitor 42"
       ::= { siteMonitor 42 }

   siteMonitor43 OBJECT-TYPE
       SYNTAX     INTEGER {
           off(0),
           on(1)
       }
       MAX-ACCESS read-only
       STATUS     current
       DESCRIPTION
               "SiteMonitor 43"
       ::= { siteMonitor 43 }

   siteMonitor44 OBJECT-TYPE
       SYNTAX     INTEGER {
           off(0),
           on(1)
       }
       MAX-ACCESS read-only
       STATUS     current
       DESCRIPTION
               "SiteMonitor 44"
       ::= { siteMonitor 44 }

   siteMonitor45 OBJECT-TYPE
       SYNTAX     INTEGER {
           off(0),
           on(1)
       }
       MAX-ACCESS read-only
       STATUS     current
       DESCRIPTION
               "SiteMonitor 45"
       ::= { siteMonitor 45 }

   siteMonitor46 OBJECT-TYPE
       SYNTAX     INTEGER {
           off(0),
           on(1)
       }
       MAX-ACCESS read-only
       STATUS     current
       DESCRIPTION
               "SiteMonitor 46"
       ::= { siteMonitor 46 }

   siteMonitor47 OBJECT-TYPE
       SYNTAX     INTEGER {
           off(0),
           on(1)
       }
       MAX-ACCESS read-only
       STATUS     current
       DESCRIPTION
               "SiteMonitor 47"
       ::= { siteMonitor 47 }

   siteMonitor48 OBJECT-TYPE
       SYNTAX     INTEGER {
           off(0),
           on(1)
       }
       MAX-ACCESS read-only
       STATUS     current
       DESCRIPTION
               "SiteMonitor 48"
       ::= { siteMonitor 48 }

   siteMonitor49 OBJECT-TYPE
       SYNTAX     INTEGER {
           off(0),
           on(1)
       }
       MAX-ACCESS read-only
       STATUS     current
       DESCRIPTION
               "SiteMonitor 49"
       ::= { siteMonitor 49 }

   siteMonitor50 OBJECT-TYPE
       SYNTAX     INTEGER {
           off(0),
           on(1)
       }
       MAX-ACCESS read-only
       STATUS     current
       DESCRIPTION
               "SiteMonitor 50"
       ::= { siteMonitor 50 }

   siteMonitor51 OBJECT-TYPE
       SYNTAX     INTEGER {
           off(0),
           on(1)
       }
       MAX-ACCESS read-only
       STATUS     current
       DESCRIPTION
               "SiteMonitor 51"
       ::= { siteMonitor 51 }

   siteMonitor52 OBJECT-TYPE
       SYNTAX     INTEGER {
           off(0),
           on(1)
       }
       MAX-ACCESS read-only
       STATUS     current
       DESCRIPTION
               "SiteMonitor 52"
       ::= { siteMonitor 52 }

   siteMonitor53 OBJECT-TYPE
       SYNTAX     INTEGER {
           off(0),
           on(1)
       }
       MAX-ACCESS read-only
       STATUS     current
       DESCRIPTION
               "SiteMonitor 53"
       ::= { siteMonitor 53 }

   siteMonitor54 OBJECT-TYPE
       SYNTAX     INTEGER {
           off(0),
           on(1)
       }
       MAX-ACCESS read-only
       STATUS     current
       DESCRIPTION
               "SiteMonitor 54"
       ::= { siteMonitor 54 }

   siteMonitor55 OBJECT-TYPE
       SYNTAX     INTEGER {
           off(0),
           on(1)
       }
       MAX-ACCESS read-only
       STATUS     current
       DESCRIPTION
               "SiteMonitor 55"
       ::= { siteMonitor 55 }

   siteMonitor56 OBJECT-TYPE
       SYNTAX     INTEGER {
           off(0),
           on(1)
       }
       MAX-ACCESS read-only
       STATUS     current
       DESCRIPTION
               "SiteMonitor 56"
       ::= { siteMonitor 56 }

   siteMonitor57 OBJECT-TYPE
       SYNTAX     INTEGER {
           off(0),
           on(1)
       }
       MAX-ACCESS read-only
       STATUS     current
       DESCRIPTION
               "SiteMonitor 57"
       ::= { siteMonitor 57 }

   siteMonitor58 OBJECT-TYPE
       SYNTAX     INTEGER {
           off(0),
           on(1)
       }
       MAX-ACCESS read-only
       STATUS     current
       DESCRIPTION
               "SiteMonitor 58"
       ::= { siteMonitor 58 }

   siteMonitor59 OBJECT-TYPE
       SYNTAX     INTEGER {
           off(0),
           on(1)
       }
       MAX-ACCESS read-only
       STATUS     current
       DESCRIPTION
               "SiteMonitor 59"
       ::= { siteMonitor 59 }

   siteMonitor60 OBJECT-TYPE
       SYNTAX     INTEGER {
           off(0),
           on(1)
       }
       MAX-ACCESS read-only
       STATUS     current
       DESCRIPTION
               "SiteMonitor 60"
       ::= { siteMonitor 60 }

   siteMonitor61 OBJECT-TYPE
       SYNTAX     INTEGER {
           off(0),
           on(1)
       }
       MAX-ACCESS read-only
       STATUS     current
       DESCRIPTION
               "SiteMonitor 61"
       ::= { siteMonitor 61 }

   siteMonitor62 OBJECT-TYPE
       SYNTAX     INTEGER {
           off(0),
           on(1)
       }
       MAX-ACCESS read-only
       STATUS     current
       DESCRIPTION
               "SiteMonitor 62"
       ::= { siteMonitor 62 }

   siteMonitor63 OBJECT-TYPE
       SYNTAX     INTEGER {
           off(0),
           on(1)
       }
       MAX-ACCESS read-only
       STATUS     current
       DESCRIPTION
               "SiteMonitor 63"
       ::= { siteMonitor 63 }

   siteMonitor64 OBJECT-TYPE
       SYNTAX     INTEGER {
           off(0),
           on(1)
       }
       MAX-ACCESS read-only
       STATUS     current
       DESCRIPTION
               "SiteMonitor 64"
       ::= { siteMonitor 64 }

   --
   -- The AUX group.
   --
   aux             OBJECT IDENTIFIER ::= { upsObjects 11 }

   auxPort1 OBJECT-TYPE
       SYNTAX     INTEGER {
           off(0),
           on(1)
       }
       MAX-ACCESS read-write
       STATUS     current
       DESCRIPTION
               "AUX-Port 1"
       ::= { aux 1 }

   auxPort2 OBJECT-TYPE
       SYNTAX     INTEGER {
           off(0),
           on(1)
       }
       MAX-ACCESS read-write
       STATUS     current
       DESCRIPTION
               "AUX-Port 2"
       ::= { aux 2 }

   auxPort3 OBJECT-TYPE
       SYNTAX     INTEGER {
           off(0),
           on(1)
       }
       MAX-ACCESS read-write
       STATUS     current
       DESCRIPTION
               "AUX-Port 3"
       ::= { aux 3 }

   auxPort4 OBJECT-TYPE
       SYNTAX     INTEGER {
           off(0),
           on(1)
       }
       MAX-ACCESS read-write
       STATUS     current
       DESCRIPTION
               "AUX-Port 4"
       ::= { aux 4 }


   --
   -- The SensorMan group.
   --
   sensorMan           OBJECT IDENTIFIER ::= { upsObjects 12 }

   sensor1           OBJECT IDENTIFIER ::= { sensorMan 1 }

   sensorMan1Value OBJECT-TYPE
       SYNTAX     INTEGER
       UNITS      "0.1 units"
       MAX-ACCESS read-only
       STATUS     current
       DESCRIPTION
               "SensorMan Value 1"
       ::= { sensor1 1 }

   sensorMan1Location OBJECT-TYPE
       SYNTAX     DisplayString (SIZE (0..79))
       MAX-ACCESS read-write
       STATUS     current
       DESCRIPTION
               "SensorMan Location 1"
       ::= { sensor1 2 }

   sensorMan1Unit OBJECT-TYPE
       SYNTAX     DisplayString (SIZE (0..63))
       MAX-ACCESS read-write
       STATUS     current
       DESCRIPTION
               "SensorMan Unit 1"
       ::= { sensor1 3 }

   sensorMan1ThresholdLow OBJECT-TYPE
       SYNTAX     INTEGER
       UNITS      "0.1 units"
       MAX-ACCESS read-write
       STATUS     current
       DESCRIPTION
               "SensorMan Lower Threshold 1"
       ::= { sensor1 4 }

   sensorMan1ThresholdHigh OBJECT-TYPE
       SYNTAX     INTEGER
       UNITS      "0.1 units"
       MAX-ACCESS read-write
       STATUS     current
       DESCRIPTION
               "SensorMan Upper Threshold 1"
       ::= { sensor1 5 }

   sensorMan1Scaling OBJECT-TYPE
       SYNTAX     INTEGER
       UNITS      "0.01 units"
       MAX-ACCESS read-write
       STATUS     current
       DESCRIPTION
               "SensorMan Scaling Factor 1"
       ::= { sensor1 6 }

   sensorMan1Offset OBJECT-TYPE
       SYNTAX     INTEGER
       UNITS      "0.1 units"
       MAX-ACCESS read-write
       STATUS     current
       DESCRIPTION
               "SensorMan Offset 1"
       ::= { sensor1 7 }

   sensor2           OBJECT IDENTIFIER ::= { sensorMan 2 }

   sensorMan2Value OBJECT-TYPE
       SYNTAX     INTEGER
       UNITS      "0.1 units"
       MAX-ACCESS read-only
       STATUS     current
       DESCRIPTION
               "SensorMan Value 2"
       ::= { sensor2 1 }

   sensorMan2Location OBJECT-TYPE
       SYNTAX     DisplayString (SIZE (0..79))
       MAX-ACCESS read-write
       STATUS     current
       DESCRIPTION
               "SensorMan Location 2"
       ::= { sensor2 2 }

   sensorMan2Unit OBJECT-TYPE
       SYNTAX     DisplayString (SIZE (0..63))
       MAX-ACCESS read-write
       STATUS     current
       DESCRIPTION
               "SensorMan Unit 2"
       ::= { sensor2 3 }

   sensorMan2ThresholdLow OBJECT-TYPE
       SYNTAX     INTEGER
       UNITS      "0.1 units"
       MAX-ACCESS read-write
       STATUS     current
       DESCRIPTION
               "SensorMan Lower Threshold 2"
       ::= { sensor2 4 }

   sensorMan2ThresholdHigh OBJECT-TYPE
       SYNTAX     INTEGER
       UNITS      "0.1 units"
       MAX-ACCESS read-write
       STATUS     current
       DESCRIPTION
               "SensorMan Upper Threshold 2"
       ::= { sensor2 5 }

   sensorMan2Scaling OBJECT-TYPE
       SYNTAX     INTEGER
       UNITS      "0.01 units"
       MAX-ACCESS read-write
       STATUS     current
       DESCRIPTION
               "SensorMan Scaling Factor 2"
       ::= { sensor2 6 }

   sensorMan2Offset OBJECT-TYPE
       SYNTAX     INTEGER
       UNITS      "0.1 units"
       MAX-ACCESS read-write
       STATUS     current
       DESCRIPTION
               "SensorMan Offset 2"
       ::= { sensor2 7 }

   sensor3           OBJECT IDENTIFIER ::= { sensorMan 3 }

   sensorMan3Value OBJECT-TYPE
       SYNTAX     INTEGER
       UNITS      "0.1 units"
       MAX-ACCESS read-only
       STATUS     current
       DESCRIPTION
               "SensorMan Value 3"
       ::= { sensor3 1 }

   sensorMan3Location OBJECT-TYPE
       SYNTAX     DisplayString (SIZE (0..79))
       MAX-ACCESS read-write
       STATUS     current
       DESCRIPTION
               "SensorMan Location 3"
       ::= { sensor3 2 }

   sensorMan3Unit OBJECT-TYPE
       SYNTAX     DisplayString (SIZE (0..63))
       MAX-ACCESS read-write
       STATUS     current
       DESCRIPTION
               "SensorMan Unit 3"
       ::= { sensor3 3 }

   sensorMan3ThresholdLow OBJECT-TYPE
       SYNTAX     INTEGER
       UNITS      "0.1 units"
       MAX-ACCESS read-write
       STATUS     current
       DESCRIPTION
               "SensorMan Lower Threshold 3"
       ::= { sensor3 4 }

   sensorMan3ThresholdHigh OBJECT-TYPE
       SYNTAX     INTEGER
       UNITS      "0.1 units"
       MAX-ACCESS read-write
       STATUS     current
       DESCRIPTION
               "SensorMan Upper Threshold 3"
       ::= { sensor3 5 }

   sensorMan3Scaling OBJECT-TYPE
       SYNTAX     INTEGER
       UNITS      "0.01 units"
       MAX-ACCESS read-write
       STATUS     current
       DESCRIPTION
               "SensorMan Scaling Factor 3"
       ::= { sensor3 6 }

   sensorMan3Offset OBJECT-TYPE
       SYNTAX     INTEGER
       UNITS      "0.1 units"
       MAX-ACCESS read-write
       STATUS     current
       DESCRIPTION
               "SensorMan Offset 3"
       ::= { sensor3 7 }

   sensor4           OBJECT IDENTIFIER ::= { sensorMan 4 }

   sensorMan4Value OBJECT-TYPE
       SYNTAX     INTEGER
       UNITS      "0.1 units"
       MAX-ACCESS read-only
       STATUS     current
       DESCRIPTION
               "SensorMan Value 4"
       ::= { sensor4 1 }

   sensorMan4Location OBJECT-TYPE
       SYNTAX     DisplayString (SIZE (0..79))
       MAX-ACCESS read-write
       STATUS     current
       DESCRIPTION
               "SensorMan Location 4"
       ::= { sensor4 2 }

   sensorMan4Unit OBJECT-TYPE
       SYNTAX     DisplayString (SIZE (0..63))
       MAX-ACCESS read-write
       STATUS     current
       DESCRIPTION
               "SensorMan Unit 4"
       ::= { sensor4 3 }

   sensorMan4ThresholdLow OBJECT-TYPE
       SYNTAX     INTEGER
       UNITS      "0.1 units"
       MAX-ACCESS read-write
       STATUS     current
       DESCRIPTION
               "SensorMan Lower Threshold 4"
       ::= { sensor4 4 }

   sensorMan4ThresholdHigh OBJECT-TYPE
       SYNTAX     INTEGER
       UNITS      "0.1 units"
       MAX-ACCESS read-write
       STATUS     current
       DESCRIPTION
               "SensorMan Upper Threshold 4"
       ::= { sensor4 5 }

   sensorMan4Scaling OBJECT-TYPE
       SYNTAX     INTEGER
       UNITS      "0.01 units"
       MAX-ACCESS read-write
       STATUS     current
       DESCRIPTION
               "SensorMan Scaling Factor 4"
       ::= { sensor4 6 }

   sensorMan4Offset OBJECT-TYPE
       SYNTAX     INTEGER
       UNITS      "0.1 units"
       MAX-ACCESS read-write
       STATUS     current
       DESCRIPTION
               "SensorMan Offset 4"
       ::= { sensor4 7 }

   sensor5           OBJECT IDENTIFIER ::= { sensorMan 5 }

   sensorMan5Value OBJECT-TYPE
       SYNTAX     INTEGER
       UNITS      "0.1 units"
       MAX-ACCESS read-only
       STATUS     current
       DESCRIPTION
               "SensorMan Value 5"
       ::= { sensor5 1 }

   sensorMan5Location OBJECT-TYPE
       SYNTAX     DisplayString (SIZE (0..79))
       MAX-ACCESS read-write
       STATUS     current
       DESCRIPTION
               "SensorMan Location 5"
       ::= { sensor5 2 }

   sensorMan5Unit OBJECT-TYPE
       SYNTAX     DisplayString (SIZE (0..63))
       MAX-ACCESS read-write
       STATUS     current
       DESCRIPTION
               "SensorMan Unit 5"
       ::= { sensor5 3 }

   sensorMan5ThresholdLow OBJECT-TYPE
       SYNTAX     INTEGER
       UNITS      "0.1 units"
       MAX-ACCESS read-write
       STATUS     current
       DESCRIPTION
               "SensorMan Lower Threshold 5"
       ::= { sensor5 4 }

   sensorMan5ThresholdHigh OBJECT-TYPE
       SYNTAX     INTEGER
       UNITS      "0.1 units"
       MAX-ACCESS read-write
       STATUS     current
       DESCRIPTION
               "SensorMan Upper Threshold 5"
       ::= { sensor5 5 }

   sensorMan5Scaling OBJECT-TYPE
       SYNTAX     INTEGER
       UNITS      "0.01 units"
       MAX-ACCESS read-write
       STATUS     current
       DESCRIPTION
               "SensorMan Scaling Factor 5"
       ::= { sensor5 6 }

   sensorMan5Offset OBJECT-TYPE
       SYNTAX     INTEGER
       UNITS      "0.1 units"
       MAX-ACCESS read-write
       STATUS     current
       DESCRIPTION
               "SensorMan Offset 5"
       ::= { sensor5 7 }

   sensor6           OBJECT IDENTIFIER ::= { sensorMan 6 }

   sensorMan6Value OBJECT-TYPE
       SYNTAX     INTEGER
       UNITS      "0.1 units"
       MAX-ACCESS read-only
       STATUS     current
       DESCRIPTION
               "SensorMan Value 6"
       ::= { sensor6 1 }

   sensorMan6Location OBJECT-TYPE
       SYNTAX     DisplayString (SIZE (0..79))
       MAX-ACCESS read-write
       STATUS     current
       DESCRIPTION
               "SensorMan Location 6"
       ::= { sensor6 2 }

   sensorMan6Unit OBJECT-TYPE
       SYNTAX     DisplayString (SIZE (0..63))
       MAX-ACCESS read-write
       STATUS     current
       DESCRIPTION
               "SensorMan Unit 6"
       ::= { sensor6 3 }

   sensorMan6ThresholdLow OBJECT-TYPE
       SYNTAX     INTEGER
       UNITS      "0.1 units"
       MAX-ACCESS read-write
       STATUS     current
       DESCRIPTION
               "SensorMan Lower Threshold 6"
       ::= { sensor6 4 }

   sensorMan6ThresholdHigh OBJECT-TYPE
       SYNTAX     INTEGER
       UNITS      "0.1 units"
       MAX-ACCESS read-write
       STATUS     current
       DESCRIPTION
               "SensorMan Upper Threshold 6"
       ::= { sensor6 5 }

   sensorMan6Scaling OBJECT-TYPE
       SYNTAX     INTEGER
       UNITS      "0.01 units"
       MAX-ACCESS read-write
       STATUS     current
       DESCRIPTION
               "SensorMan Scaling Factor 6"
       ::= { sensor6 6 }

   sensorMan6Offset OBJECT-TYPE
       SYNTAX     INTEGER
       UNITS      "0.1 units"
       MAX-ACCESS read-write
       STATUS     current
       DESCRIPTION
               "SensorMan Offset 6"
       ::= { sensor6 7 }

   sensor7           OBJECT IDENTIFIER ::= { sensorMan 7 }

   sensorMan7Value OBJECT-TYPE
       SYNTAX     INTEGER
       UNITS      "0.1 units"
       MAX-ACCESS read-only
       STATUS     current
       DESCRIPTION
               "SensorMan Value 7"
       ::= { sensor7 1 }

   sensorMan7Location OBJECT-TYPE
       SYNTAX     DisplayString (SIZE (0..79))
       MAX-ACCESS read-write
       STATUS     current
       DESCRIPTION
               "SensorMan Location 7"
       ::= { sensor7 2 }

   sensorMan7Unit OBJECT-TYPE
       SYNTAX     DisplayString (SIZE (0..63))
       MAX-ACCESS read-write
       STATUS     current
       DESCRIPTION
               "SensorMan Unit 7"
       ::= { sensor7 3 }

   sensorMan7ThresholdLow OBJECT-TYPE
       SYNTAX     INTEGER
       UNITS      "0.1 units"
       MAX-ACCESS read-write
       STATUS     current
       DESCRIPTION
               "SensorMan Lower Threshold 7"
       ::= { sensor7 4 }

   sensorMan7ThresholdHigh OBJECT-TYPE
       SYNTAX     INTEGER
       UNITS      "0.1 units"
       MAX-ACCESS read-write
       STATUS     current
       DESCRIPTION
               "SensorMan Upper Threshold 7"
       ::= { sensor7 5 }

   sensorMan7Scaling OBJECT-TYPE
       SYNTAX     INTEGER
       UNITS      "0.01 units"
       MAX-ACCESS read-write
       STATUS     current
       DESCRIPTION
               "SensorMan Scaling Factor 7"
       ::= { sensor7 6 }

   sensorMan7Offset OBJECT-TYPE
       SYNTAX     INTEGER
       UNITS      "0.1 units"
       MAX-ACCESS read-write
       STATUS     current
       DESCRIPTION
               "SensorMan Offset 7"
       ::= { sensor7 7 }

   sensor8           OBJECT IDENTIFIER ::= { sensorMan 8 }

   sensorMan8Value OBJECT-TYPE
       SYNTAX     INTEGER
       UNITS      "0.1 units"
       MAX-ACCESS read-only
       STATUS     current
       DESCRIPTION
               "SensorMan Value 8"
       ::= { sensor8 1 }

   sensorMan8Location OBJECT-TYPE
       SYNTAX     DisplayString (SIZE (0..79))
       MAX-ACCESS read-write
       STATUS     current
       DESCRIPTION
               "SensorMan Location 8"
       ::= { sensor8 2 }

   sensorMan8Unit OBJECT-TYPE
       SYNTAX     DisplayString (SIZE (0..63))
       MAX-ACCESS read-write
       STATUS     current
       DESCRIPTION
               "SensorMan Unit 8"
       ::= { sensor8 3 }

   sensorMan8ThresholdLow OBJECT-TYPE
       SYNTAX     INTEGER
       UNITS      "0.1 units"
       MAX-ACCESS read-write
       STATUS     current
       DESCRIPTION
               "SensorMan Lower Threshold 8"
       ::= { sensor8 4 }

   sensorMan8ThresholdHigh OBJECT-TYPE
       SYNTAX     INTEGER
       UNITS      "0.1 units"
       MAX-ACCESS read-write
       STATUS     current
       DESCRIPTION
               "SensorMan Upper Threshold 8"
       ::= { sensor8 5 }

   sensorMan8Scaling OBJECT-TYPE
       SYNTAX     INTEGER
       UNITS      "0.01 units"
       MAX-ACCESS read-write
       STATUS     current
       DESCRIPTION
               "SensorMan Scaling Factor 8"
       ::= { sensor8 6 }

   sensorMan8Offset OBJECT-TYPE
       SYNTAX     INTEGER
       UNITS      "0.1 units"
       MAX-ACCESS read-write
       STATUS     current
       DESCRIPTION
               "SensorMan Offset 8"
       ::= { sensor8 7 }

   input1         OBJECT IDENTIFIER ::= { sensorMan 9 }

   input1Value OBJECT-TYPE
       SYNTAX     INTEGER {
           off(0),
           on(1)
       }
       MAX-ACCESS read-only
       STATUS     current
       DESCRIPTION
               "SensorMan Input 1"
       ::= { input1 1 }

   input1Location OBJECT-TYPE
       SYNTAX     DisplayString (SIZE (0..79))
       MAX-ACCESS read-write
       STATUS     current
       DESCRIPTION
               "SensorMan Input 1 Location"
       ::= { input1 2 }

   input1NCContact OBJECT-TYPE
       SYNTAX     INTEGER {
           no(0),
           yes(1)
       }
       MAX-ACCESS read-write
       STATUS     current
       DESCRIPTION
               "SensorMan Input 1 is used as NC contact"
       ::= { input1 3 }

   input2         OBJECT IDENTIFIER ::= { sensorMan 10 }

   input2Value OBJECT-TYPE
       SYNTAX     INTEGER {
           off(0),
           on(1)
       }
       MAX-ACCESS read-only
       STATUS     current
       DESCRIPTION
               "SensorMan Input 2"
       ::= { input2 1 }

   input2Location OBJECT-TYPE
       SYNTAX     DisplayString (SIZE (0..79))
       MAX-ACCESS read-write
       STATUS     current
       DESCRIPTION
               "SensorMan Input 2 Location"
       ::= { input2 2 }

   input2NCContact OBJECT-TYPE
       SYNTAX     INTEGER {
           no(0),
           yes(1)
       }
       MAX-ACCESS read-only
       STATUS     current
       DESCRIPTION
               "SensorMan Input 2 is used as NC contact"
       ::= { input2 3 }

   input3         OBJECT IDENTIFIER ::= { sensorMan 11 }

   input3Value OBJECT-TYPE
       SYNTAX     INTEGER {
           off(0),
           on(1)
       }
       MAX-ACCESS read-write
       STATUS     current
       DESCRIPTION
               "SensorMan Input 3"
       ::= { input3 1 }

   input3Location OBJECT-TYPE
       SYNTAX     DisplayString (SIZE (0..79))
       MAX-ACCESS read-write
       STATUS     current
       DESCRIPTION
               "SensorMan Input 3 Location"
       ::= { input3 2 }

   input3NCContact OBJECT-TYPE
       SYNTAX     INTEGER {
           no(0),
           yes(1)
       }
       MAX-ACCESS read-write
       STATUS     current
       DESCRIPTION
               "SensorMan Input 3 is used as NC contact"
       ::= { input3 3 }

   input4         OBJECT IDENTIFIER ::= { sensorMan 12 }

   input4Value OBJECT-TYPE
       SYNTAX     INTEGER {
           off(0),
           on(1)
       }
       MAX-ACCESS read-only
       STATUS     current
       DESCRIPTION
               "SensorMan Input 4"
       ::= { input4 1 }

   input4Location OBJECT-TYPE
       SYNTAX     DisplayString (SIZE (0..79))
       MAX-ACCESS read-write
       STATUS     current
       DESCRIPTION
               "SensorMan Input 4 Location"
       ::= { input4 2 }

   input4NCContact OBJECT-TYPE
       SYNTAX     INTEGER {
           no(0),
           yes(1)
       }
       MAX-ACCESS read-write
       STATUS     current
       DESCRIPTION
               "SensorMan Input 4 is used as NC contact"
       ::= { input4 3 }

   output1        OBJECT IDENTIFIER ::= { sensorMan 13 }

   output1Value OBJECT-TYPE
       SYNTAX     INTEGER {
           off(0),
           on(1)
       }
       MAX-ACCESS read-write
       STATUS     current
       DESCRIPTION
               "SensorMan Output 1"
       ::= { output1 1 }

   output1Location OBJECT-TYPE
       SYNTAX     DisplayString (SIZE (0..79))
       MAX-ACCESS read-write
       STATUS     current
       DESCRIPTION
               "SensorMan Output 1 Location"
       ::= { output1 2 }

   output1NCContact OBJECT-TYPE
       SYNTAX     INTEGER {
           no(0),
           yes(1)
       }
       MAX-ACCESS read-write
       STATUS     current
       DESCRIPTION
               "SensorMan Output 1 is used as NC contact"
       ::= { output1 3 }

   output2        OBJECT IDENTIFIER ::= { sensorMan 14 }

   output2Value OBJECT-TYPE
       SYNTAX     INTEGER {
           off(0),
           on(1)
       }
       MAX-ACCESS read-write
       STATUS     current
       DESCRIPTION
               "SensorMan Output 2"
       ::= { output2 1 }

   output2Location OBJECT-TYPE
       SYNTAX     DisplayString (SIZE (0..79))
       MAX-ACCESS read-write
       STATUS     current
       DESCRIPTION
               "SensorMan Output 2 Location"
       ::= { output2 2 }

   output2NCContact OBJECT-TYPE
       SYNTAX     INTEGER {
           no(0),
           yes(1)
       }
       MAX-ACCESS read-write
       STATUS     current
       DESCRIPTION
               "SensorMan Output 2 is used as NC contact"
       ::= { output2 3 }

   output3        OBJECT IDENTIFIER ::= { sensorMan 15 }

   output3Value OBJECT-TYPE
       SYNTAX     INTEGER {
           off(0),
           on(1)
       }
       MAX-ACCESS read-write
       STATUS     current
       DESCRIPTION
               "SensorMan Output 3"
       ::= { output3 1 }

   output3Location OBJECT-TYPE
       SYNTAX     DisplayString (SIZE (0..79))
       MAX-ACCESS read-write
       STATUS     current
       DESCRIPTION
               "SensorMan Output 3 Location"
       ::= { output3 2 }

   output3NCContact OBJECT-TYPE
       SYNTAX     INTEGER {
           no(0),
           yes(1)
       }
       MAX-ACCESS read-write
       STATUS     current
       DESCRIPTION
               "SensorMan Output 3 is used as NC contact"
       ::= { output3 3 }

   output4        OBJECT IDENTIFIER ::= { sensorMan 16 }

   output4Value OBJECT-TYPE
       SYNTAX     INTEGER {
           off(0),
           on(1)
       }
       MAX-ACCESS read-write
       STATUS     current
       DESCRIPTION
               "SensorMan Output 4"
       ::= { output4 1 }

   output4Location OBJECT-TYPE
       SYNTAX     DisplayString (SIZE (0..79))
       MAX-ACCESS read-write
       STATUS     current
       DESCRIPTION
               "SensorMan Output 4 Location"
       ::= { output4 2 }

   output4NCContact OBJECT-TYPE
       SYNTAX     INTEGER {
           no(0),
           yes(1)
       }
       MAX-ACCESS read-write
       STATUS     current
       DESCRIPTION
               "SensorMan Output 4 is used as NC contact"
       ::= { output4 3 }

   --
   -- notifications, i.e., traps
   --
   upsTraps              OBJECT IDENTIFIER ::= { upsMIB 2 }

   -- This section defines the well-known notifications sent by
   -- UPS agents.
   -- Care must be taken to insure that no particular notification
   -- is sent to a single receiving entity more often than once
   -- every five seconds.

   upsTrapOnBattery NOTIFICATION-TYPE
       OBJECTS { upsEstimatedMinutesRemaining, upsSecondsOnBattery,
                 upsConfigLowBattTime }
       STATUS  current
       DESCRIPTION
               "The UPS is operating on battery power.  This trap is
               persistent and is resent at one minute intervals until
               the UPS either turns off or is no longer running on
               battery."
     ::= { upsTraps 1 }

   upsTrapTestCompleted NOTIFICATION-TYPE
       OBJECTS { upsTestId, upsTestSpinLock,
                 upsTestResultsSummary, upsTestResultsDetail,
                 upsTestStartTime, upsTestElapsedTime }
       STATUS  current
       DESCRIPTION
               "This trap is sent upon completion of a UPS diagnostic
               test."
     ::= { upsTraps 2 }

   upsTrapAlarmEntryAdded NOTIFICATION-TYPE
       OBJECTS { upsAlarmId, upsAlarmDescr }
       STATUS  current
       DESCRIPTION
               "This trap is sent each time an alarm is inserted into
               to the alarm table.  It is sent on the insertion of
               all alarms except for upsAlarmOnBattery and
               upsAlarmTestInProgress."
     ::= { upsTraps 3 }

   upsTrapAlarmEntryRemoved NOTIFICATION-TYPE
       OBJECTS { upsAlarmId, upsAlarmDescr }
       STATUS  current
       DESCRIPTION
               "This trap is sent each time an alarm is removed from
               the alarm table.  It is sent on the removal of all
               alarms except for upsAlarmTestInProgress."
     ::= { upsTraps 4 }


   --
   -- conformance information
   --
   upsConformance        OBJECT IDENTIFIER ::= { upsMIB 3 }

   upsCompliances        OBJECT IDENTIFIER ::= { upsConformance 1 }


   --
   -- compliance statements
   --

   upsSubsetCompliance MODULE-COMPLIANCE
       STATUS     current
       DESCRIPTION

               "The compliance statement for UPSs that only support
               the two-contact communication protocol."
       MODULE -- this module
           MANDATORY-GROUPS  { upsSubsetIdentGroup,
                     upsSubsetBatteryGroup, upsSubsetInputGroup,
                     upsSubsetOutputGroup, upsSubsetAlarmGroup,
                     upsSubsetControlGroup, upsSubsetConfigGroup }

       OBJECT     upsBatteryStatus
       SYNTAX     INTEGER {
           batteryNormal(2),
           batteryLow(3)
       }
       DESCRIPTION
               "Support of the values unknown(1) and
               batteryDepleted(4) is not required."

       OBJECT     upsAlarmDescr
       DESCRIPTION
               "Support of all `well known' alarm types is not
               required.  The well known alarm types which must be
               supported are: upsAlarmOnBattery, upsAlarmLowBattery,
               upsAlarmInputBad, upsAlarmUpsOutputOff,
               upsAlarmUpsSystemOff, and upsAlarmTestInProgress."

       OBJECT     upsOutputSource
       SYNTAX     INTEGER {
           normal(2),
           battery(4)
       }
       DESCRIPTION
               "Support of the values other(1), none(2), bypass(4),
               booster(6) and reducer(7) is not required."

       OBJECT     upsShutdownType
       MIN-ACCESS read-only
       DESCRIPTION
               "Read-write access is not required, i.e., compliant
               systems need not support more than one shutdown type."

       OBJECT     upsAutoRestart
       MIN-ACCESS read-only
       DESCRIPTION
               "Read-write access is not required, i.e., compliant
               systems need not support more than one restart type."

       OBJECT     upsConfigInputVoltage
       MIN-ACCESS read-only
       DESCRIPTION
               "Read-write access is not required."

       OBJECT     upsConfigInputFreq
       MIN-ACCESS read-only
       DESCRIPTION
               "Read-write access is not required."

       OBJECT     upsConfigOutputVoltage
       MIN-ACCESS read-only
       DESCRIPTION
               "Read-write access is not required."

       OBJECT     upsConfigOutputFreq
       MIN-ACCESS read-only
       DESCRIPTION
               "Read-write access is not required."

       ::= { upsCompliances 1 }

   upsBasicCompliance MODULE-COMPLIANCE
       STATUS     current
       DESCRIPTION

               "The compliance statement for UPSs that support
               full-featured functions, such as control."
       MODULE -- this module
           MANDATORY-GROUPS { upsBasicIdentGroup,
                     upsBasicBatteryGroup, upsBasicInputGroup,
                     upsBasicOutputGroup, upsBasicAlarmGroup,
                     upsBasicTestGroup, upsBasicControlGroup,
                     upsBasicConfigGroup }


       OBJECT     upsAlarmDescr
       DESCRIPTION
               "Support of all `well known' alarm types is not
               required.  The well known alarm types which must be
               supported are: upsAlarmOnBattery, upsAlarmLowBattery,
               upsAlarmDepletedBattery, upsAlarmTempBad,
               upsAlarmInputBad, upsAlarmOutputOverload,
               upsAlarmOnBypass, upsAlarmBypassBad,
               upsAlarmOutputOffAsRequested,
               upsAlarmUpsOffAsRequested, upsAlarmUpsOutputOff,
               upsAlarmUpsSystemOff, upsAlarmGeneralFault,
               upsAlarmDiagnosticTestFailed,
               upsAlarmCommunicationsLost, upsAlarmShutdownPending,
               and upsAlarmTestInProgress."

       OBJECT     upsTestId
       DESCRIPTION
               "Support of all `well known' test types is not
               required.  If no tests are supported, then the only
               well known test type which must be supported is
               upsTestNoTestsInitiated."

       OBJECT     upsOutputSource
       SYNTAX     INTEGER {
           normal(2),
           battery(4)
       }
       DESCRIPTION
               "Support of the values other(1), none(2), bypass(4),
               booster(6) and reducer(7) is not required."

           GROUP upsBasicBypassGroup
           DESCRIPTION
               "The upsBasicBypassGroup is only required for UPSs
               that have a Bypass present."
       OBJECT     upsShutdownType
       MIN-ACCESS read-only
       DESCRIPTION
               "Read-write access is not required, i.e., compliant
               systems need not support more than one shutdown type."

       OBJECT     upsAutoRestart
       MIN-ACCESS read-only
       DESCRIPTION
               "Read-write access is not required, i.e., compliant
               systems need not support more than one restart type."

       OBJECT     upsConfigInputVoltage
       MIN-ACCESS read-only
       DESCRIPTION
               "Read-write access is not required."

       OBJECT     upsConfigInputFreq
       MIN-ACCESS read-only
       DESCRIPTION
               "Read-write access is not required."

       OBJECT     upsConfigOutputVoltage
       MIN-ACCESS read-only
       DESCRIPTION
               "Read-write access is not required."

       OBJECT     upsConfigOutputFreq
       MIN-ACCESS read-only
       DESCRIPTION
               "Read-write access is not required."

       OBJECT     upsConfigLowBattTime
       DESCRIPTION
               "Implementation of all possible values may be onerous
               for some systems.  Consequently, not all possible
               values must be supported.  However, at least two
               different manufacturer-selected values must be
               supported."

       ::= { upsCompliances 2 }

   upsFullCompliance MODULE-COMPLIANCE
       STATUS     current
       DESCRIPTION
               "The compliance statement for UPSs that support
               advanced full-featured functions."
       MODULE -- this module
           MANDATORY-GROUPS { upsFullIdentGroup, upsFullBatteryGroup,
                     upsFullInputGroup, upsFullOutputGroup,
                     upsFullAlarmGroup, upsFullTestGroup,
                     upsFullControlGroup, upsFullConfigGroup }

       OBJECT     upsAlarmDescr
       DESCRIPTION
               "Support of all `well known' alarm types is not
               required.  The well known alarm types which must be
               supported are: upsAlarmBatteryBad, upsAlarmOnBattery,
               upsAlarmLowBattery, upsAlarmDepletedBattery,
               upsAlarmTempBad, upsAlarmInputBad, upsAlarmOnBypass,
               upsAlarmBypassBad, upsAlarmOutputOffAsRequested,
               upsAlarmUpsOffAsRequested, upsAlarmUpsOutputOff,
               upsAlarmUpsSystemOff, upsAlarmGeneralFault,
               upsAlarmDiagnosticTestFailed,
               upsAlarmCommunicationsLost, upsAlarmShutdownPending,
               and upsAlarmTestInProgress."

       OBJECT     upsTestId
       DESCRIPTION
               "Support of all `well known' test types is not
               required.  The well known test types which must be
               supported are: upsTestNoTestsInitiated,
               upsTestGeneralSystemsTest, and
               upsTestQuickBatteryTest."

       OBJECT     upsOutputSource
       SYNTAX     INTEGER {
           normal(2),
           battery(4)
       }
       DESCRIPTION
               "Support of the values other(1), none(2), bypass(4),
               booster(6) and reducer(7) is not required."

           GROUP upsFullBypassGroup
           DESCRIPTION
               "The upsFullBypassGroup is only required for UPSs that
               have a Bypass present."

       OBJECT     upsShutdownType
       MIN-ACCESS read-only
       DESCRIPTION
               "Read-write access is not required, i.e., compliant
               systems need not support more than one shutdown type."

       OBJECT     upsAutoRestart
       MIN-ACCESS read-only
       DESCRIPTION
               "Read-write access is not required, i.e., compliant
               systems need not support more than one restart type."

       OBJECT     upsConfigInputVoltage
       MIN-ACCESS read-only
       DESCRIPTION
               "Read-write access is not required."

       OBJECT     upsConfigInputFreq
       MIN-ACCESS read-only
       DESCRIPTION
               "Read-write access is not required."

       OBJECT     upsConfigOutputVoltage
       MIN-ACCESS read-only
       DESCRIPTION
               "Read-write access is not required."

       OBJECT     upsConfigOutputFreq
       MIN-ACCESS read-only
       DESCRIPTION
               "Read-write access is not required."

       OBJECT     upsConfigLowBattTime
       DESCRIPTION
               "Implementation of all possible values may be onerous
               for some systems.  Consequently, not all possible
               values must be supported.  However, at least two
               different manufacturer-selected values must be
               supported."

       ::= { upsCompliances 3 }


   --
   -- units of conformance
   --

   -- summary at a glance:

   --                                      subset  basic   adv
   --upsIdentManufacturer                  x       x       x
   --upsIdentModel                         x       x       x
   --upsIdentUPSSoftwareVersion                    x       x
   --upsIdentAgentSoftwareVersion          x       x       x
   --upsIdentName                          x       x       x
   --upsIdentAttachedDevices               x               x
   --
   --upsBatteryStatus                      x       x       x  notes
   --upsSecondsOnBattery                   x       x       x
   --upsEstimatedMinutesRemaining                          x
   --upsEstimatedChargeRemaining                           x
   --upsBatteryVoltage
   --upsBatteryCurrent
   --upsBatteryTemperature
   --
   --upsInputLineBads                      x       x       x
   --upsInputNumLines                              x       x
   --upsInputFrequency                             x       x
   --upsInputVoltage                               x       x
   --upsInputCurrent
   --upsInputTruePower
   --
   --upsOutputSource                       x       x       x  notes
   --upsOutputFrequency                            x       x
   --upsOutputNumLines                             x       x
   --upsOutputVoltage                              x       x
   --upsOutputCurrent                                      x
   --upsOutputPower                                        x
   --upsOutputPercentLoad                                  x
   --
   --
   --upsBypassFrequency                            x       x  notes
   --upsBypassNumLines                             x       x
   --upsBypassVoltage                              x       x
   --upsBypassCurrent
   --upsBypassPower
   --
   --
   --upsAlarmsPresent                      x       x       x
   --upsAlarmDescr                         x       x       x  notes
   --upsAlarmTime                          x       x       x
   --
   --upsTestId                                     x       x  notes
   --upsTestSpinLock                               x       x
   --upsTestResultsSummary                         x       x
   --upsTestResultsDetail                          x       x
   --upsTestStartTime                              x       x
   --upsTestElapsedTime                            x       x
   --
   --upsShutdownType                       x       x       x  notes
   --upsShutdownAfterDelay                 x       x       x
   --upsStartupAfterDelay                          x       x
   --upsRebootWithDuration                         x       x
   --upsAutoRestart                        x       x       x  notes
   --
   --upsConfigInputVoltage                 x       x       x  notes
   --upsConfigInputFreq                    x       x       x  notes
   --upsConfigOutputVoltage                x       x       x  notes
   --upsConfigOutputFreq                   x       x       x  notes
   --upsConfigOutputVA                     x       x       x
   --upsConfigOutputPower                  x       x       x
   --upsConfigLowBattTime                          x       x  notes
   --upsConfigAudibleStatus                        x       x
   --upsConfigLowVoltageTransferPoint
   --upsConfigHighVoltageTransferPoint


   -- units of conformance
   upsGroups             OBJECT IDENTIFIER ::= { upsConformance 2 }

   upsSubsetGroups       OBJECT IDENTIFIER ::= { upsGroups 1 }

   upsSubsetIdentGroup OBJECT-GROUP
       OBJECTS { upsIdentManufacturer, upsIdentModel,
                 upsIdentAgentSoftwareVersion, upsIdentName,
                 upsIdentAttachedDevices }
       STATUS  current
       DESCRIPTION
               "The upsSubsetIdentGroup defines objects which are
               common across all UPSs which meet subset compliance.
               Most devices which conform to the upsSubsetIdentGroup
               will provide access to these objects via a proxy
               agent.  If the proxy agent is compatible with multiple
               UPS types, configuration of the proxy agent will
               require specifying some of these values, either
               individually, or as a group (perhaps through a table
               lookup mechanism based on the UPS model number)."
       ::= { upsSubsetGroups 1 }

   upsSubsetBatteryGroup OBJECT-GROUP
       OBJECTS { upsBatteryStatus, upsSecondsOnBattery }
       STATUS  current
       DESCRIPTION
               "The upsSubsetBatteryGroup defines the objects that
               are common to battery groups of two-contact UPSs."
       ::= { upsSubsetGroups 2 }

   upsSubsetInputGroup OBJECT-GROUP
       OBJECTS { upsInputLineBads }
       STATUS  current
       DESCRIPTION
               "The upsSubsetInputGroup defines the objects that are
               common to the Input groups of two-contact UPSs."
       ::= { upsSubsetGroups 3 }

   upsSubsetOutputGroup OBJECT-GROUP
       OBJECTS { upsOutputSource }
       STATUS  current
       DESCRIPTION
               "The upsSubsetOutputGroup defines the objects that are
               common to the Output groups of two-contact UPSs."
       ::= { upsSubsetGroups 4 }


   -- { upsSubsetGroups 5 } is reserved for
   -- future use (upsSubsetBypassGroup)

   upsSubsetAlarmGroup OBJECT-GROUP
       OBJECTS { upsAlarmsPresent, upsAlarmDescr, upsAlarmTime }
       STATUS  current
       DESCRIPTION
               "The upsSubsetAlarmGroup defines the objects that are
               common to the Alarm groups of two-contact UPSs."
       ::= { upsSubsetGroups 6 }

   -- { upsSubsetGroups 7 } is reserved for
   -- future use (upsSubsetTestGroup)

   upsSubsetControlGroup OBJECT-GROUP
       OBJECTS { upsShutdownType, upsShutdownAfterDelay,
                     upsAutoRestart }
       STATUS  current
       DESCRIPTION
               "The upsSubsetControlGroup defines the objects that
               are common to the Control groups of two-contact UPSs."
       ::= { upsSubsetGroups 8 }

   upsSubsetConfigGroup OBJECT-GROUP
       OBJECTS { upsConfigInputVoltage, upsConfigInputFreq,
                 upsConfigOutputVoltage, upsConfigOutputFreq,
                 upsConfigOutputVA, upsConfigOutputPower }
       STATUS  current
       DESCRIPTION
               "The upsSubsetConfigGroup defines the objects that are
               common to the Config groups of two-contact UPSs."
       ::= { upsSubsetGroups 9 }
   upsBasicGroups        OBJECT IDENTIFIER ::= { upsGroups 2 }

   upsBasicIdentGroup OBJECT-GROUP
       OBJECTS { upsIdentManufacturer, upsIdentModel,
                 upsIdentUPSSoftwareVersion,
                 upsIdentAgentSoftwareVersion, upsIdentName }
       STATUS  current
       DESCRIPTION
               "The upsBasicIdentGroup defines objects which are
               common to the Ident group of compliant UPSs which
               support basic functions."
       ::= { upsBasicGroups 1 }

   upsBasicBatteryGroup OBJECT-GROUP
       OBJECTS { upsBatteryStatus, upsSecondsOnBattery }
       STATUS  current
       DESCRIPTION
               "The upsBasicBatteryGroup defines the objects that are
               common to the battery groups of compliant UPSs which
               support basic functions."
       ::= { upsBasicGroups 2 }

   upsBasicInputGroup OBJECT-GROUP
       OBJECTS { upsInputLineBads, upsInputNumLines,
                 upsInputFrequency, upsInputVoltage }
       STATUS  current
       DESCRIPTION
               "The upsBasicInputGroup defines the objects that are
               common to the Input groups of compliant UPSs which
               support basic functions."
       ::= { upsBasicGroups 3 }

   upsBasicOutputGroup OBJECT-GROUP
       OBJECTS { upsOutputSource, upsOutputFrequency,
                 upsOutputNumLines, upsOutputVoltage }
       STATUS  current
       DESCRIPTION
               "The upsBasicOutputGroup defines the objects that are
               common to the Output groups of compliant UPSs which
               support basic functions."
       ::= { upsBasicGroups 4 }

   upsBasicBypassGroup OBJECT-GROUP
       OBJECTS { upsBypassFrequency, upsBypassNumLines,
                 upsBypassVoltage }
       STATUS  current
       DESCRIPTION
               "The upsBasicBypassGroup defines the objects that are
               common to the Bypass groups of compliant UPSs which
               support basic functions."
       ::= { upsBasicGroups 5 }

   upsBasicAlarmGroup OBJECT-GROUP
       OBJECTS { upsAlarmsPresent, upsAlarmDescr, upsAlarmTime }
       STATUS  current
       DESCRIPTION

               "The upsBasicAlarmGroup defines the objects that are
               common to the Alarm  groups of compliant UPSs which
               support basic functions."
       ::= { upsBasicGroups 6 }

   upsBasicTestGroup OBJECT-GROUP
       OBJECTS { upsTestId, upsTestSpinLock,
                 upsTestResultsSummary, upsTestResultsDetail,
                 upsTestStartTime, upsTestElapsedTime }
       STATUS  current
       DESCRIPTION
               "The upsBasicTestGroup defines the objects that are
               common to the Test groups of compliant UPSs which
               support basic functions."
       ::= { upsBasicGroups 7 }

   upsBasicControlGroup OBJECT-GROUP
       OBJECTS { upsShutdownType, upsShutdownAfterDelay,
                 upsStartupAfterDelay, upsRebootWithDuration,
                 upsAutoRestart }
       STATUS  current
       DESCRIPTION
               "The upsBasicControlGroup defines the objects that are
               common to the Control groups of compliant UPSs which
               support basic functions."
       ::= { upsBasicGroups 8 }

   upsBasicConfigGroup OBJECT-GROUP
       OBJECTS { upsConfigInputVoltage, upsConfigInputFreq,
                 upsConfigOutputVoltage, upsConfigOutputFreq,
                 upsConfigOutputVA, upsConfigOutputPower,
                 upsConfigLowBattTime, upsConfigAudibleStatus }
       STATUS  current
       DESCRIPTION
               "The upsBasicConfigGroup defines the objects that are
               common to the Config groups of UPSs which support
               basic functions."
       ::= { upsBasicGroups 9 }

   upsFullGroups         OBJECT IDENTIFIER ::= { upsGroups 3 }

   upsFullIdentGroup OBJECT-GROUP
       OBJECTS { upsIdentManufacturer, upsIdentModel,
                 upsIdentUPSSoftwareVersion,
                 upsIdentAgentSoftwareVersion, upsIdentName,
                 upsIdentAttachedDevices }
       STATUS  current
       DESCRIPTION
               "The upsFullIdentGroup defines objects which are
               common to the Ident group of fully compliant UPSs."
       ::= { upsFullGroups 1 }

   upsFullBatteryGroup OBJECT-GROUP
       OBJECTS { upsBatteryStatus, upsSecondsOnBattery,
                 upsEstimatedMinutesRemaining,
                 upsEstimatedChargeRemaining }
       STATUS  current
       DESCRIPTION
               "The upsFullBatteryGroup defines the objects that are
               common to the battery groups of fully compliant UPSs."
       ::= { upsFullGroups 2 }

   upsFullInputGroup OBJECT-GROUP
       OBJECTS { upsInputLineBads, upsInputNumLines,
                 upsInputFrequency, upsInputVoltage }
       STATUS  current
       DESCRIPTION
               "The upsFullInputGroup defines the objects that are
               common to the Input groups of fully compliant UPSs."
       ::= { upsFullGroups 3 }

   upsFullOutputGroup OBJECT-GROUP
       OBJECTS { upsOutputSource, upsOutputFrequency,
                 upsOutputNumLines, upsOutputVoltage,
                 upsOutputCurrent, upsOutputPower,
                 upsOutputPercentLoad }
       STATUS  current
       DESCRIPTION
               "The upsFullOutputGroup defines the objects that are
               common to the Output groups of fully compliant UPSs."
       ::= { upsFullGroups 4 }

   upsFullBypassGroup OBJECT-GROUP
       OBJECTS { upsBypassFrequency, upsBypassNumLines,
                 upsBypassVoltage }
       STATUS  current
       DESCRIPTION
               "The upsFullBypassGroup defines the objects that are
               common to the Bypass groups of fully compliant UPSs."
       ::= { upsFullGroups 5 }

   upsFullAlarmGroup OBJECT-GROUP
       OBJECTS { upsAlarmsPresent, upsAlarmDescr, upsAlarmTime }
       STATUS  current
       DESCRIPTION

               "The upsFullAlarmGroup defines the objects that are
               common to the Alarm  groups of fully compliant UPSs."
       ::= { upsFullGroups 6 }

   upsFullTestGroup OBJECT-GROUP
       OBJECTS { upsTestId, upsTestSpinLock,
                 upsTestResultsSummary, upsTestResultsDetail,
                 upsTestStartTime, upsTestElapsedTime }
       STATUS  current
       DESCRIPTION
               "The upsFullTestGroup defines the objects that are
               common to the Test groups of fully compliant UPSs."
       ::= { upsFullGroups 7 }

   upsFullControlGroup OBJECT-GROUP
       OBJECTS { upsShutdownType, upsShutdownAfterDelay,
                 upsStartupAfterDelay, upsRebootWithDuration,
                 upsAutoRestart }
       STATUS  current
       DESCRIPTION
   "The upsFullControlGroup defines the objects that are
   common to the Control groups of fully compliant UPSs."
       ::= { upsFullGroups 8 }

   upsFullConfigGroup OBJECT-GROUP
       OBJECTS { upsConfigInputVoltage, upsConfigInputFreq,
                 upsConfigOutputVoltage, upsConfigOutputFreq,
                 upsConfigOutputVA, upsConfigOutputPower,
                 upsConfigLowBattTime, upsConfigAudibleStatus }
       STATUS  current
       DESCRIPTION
               "The upsFullConfigGroup defines the objects that are
               common to the Config groups of fully compliant UPSs."
       ::= { upsFullGroups 9 }

   END
